--
-- BYZORO-T7600.mib
-- MIB generated by MG-SOFT Visual MIB Builder Version 6.0  Build 88
-- Wednesday, September 22, 2021 at 09:34:23
--

--  BYZORO-T7600.mib
-- MIB generated by MG-SOFT Visual MIB Builder Version 6.0  Build 88
-- Monday, July 05, 2021 at 16:24:32
--
--  BYZORO-T7600.mib
-- MIB generated by MG-SOFT Visual MIB Builder Version 6.0  Build 88
-- Wednesday, February 24, 2021 at 18:21:11
--
--  BYZORO-T7600.mib
-- MIB generated by MG-SOFT Visual MIB Builder Version 6.0  Build 88
-- Wednesday, February 24, 2021 at 17:40:40
--
--  BYZORO-T7600.mib
-- MIB generated by MG-SOFT Visual MIB Builder Version 6.0  Build 88
-- Friday, January 08, 2021 at 13:43:21
--
--  BYZORO-T7600.mib
-- MIB generated by MG-SOFT Visual MIB Builder Version 6.0  Build 88
-- Monday, June 29, 2020 at 18:35:52
--

	BYZORO-T7600 DEFINITIONS ::= BEGIN

		IMPORTS
			enterprises, Integer32, Counter64, OBJECT-TYPE, MODULE-IDENTITY,
			NOTIFICATION-TYPE
				FROM SNMPv2-SMI
			DisplayString
				FROM SNMPv2-TC;


		-- 1.3.6.1.4.1.33922.106
		BYZORO-T7600 MODULE-IDENTITY
			LAST-UPDATED "201907251433Z"		-- July 25, 2019 at 14:33 GMT
			ORGANIZATION
				"byzoro"
			CONTACT-INFO
				" "
			DESCRIPTION
				" "
			::= { byzoro 106 }




--
-- Node definitions
--

--  1.3.6.1.4.1.33922.106
-- July 25, 2019 at 14:33 GMT
--
-- Node definitions
--
--  1.3.6.1.4.1.33922.106
-- July 25, 2019 at 14:33 GMT
--
-- Node definitions
--
--  1.3.6.1.4.1.33922.106
-- July 25, 2019 at 14:33 GMT
--
-- Node definitions
--
--  1.3.6.1.4.1.33922.106
-- July 25, 2019 at 14:33 GMT
--
-- Node definitions
--
--  1.3.6.1.4.1.33922.106
-- July 25, 2019 at 14:33 GMT
--
-- Node definitions
--
--  1.3.6.1.4.1.33922.106
-- July 25, 2019 at 14:33 GMT
--
-- Node definitions
--
--  1.3.6.1.4.1.33922.106
-- July 25, 2019 at 14:33 GMT
--
-- Node definitions
--
--  1.3.6.1.4.1.33922.106
-- July 25, 2019 at 14:33 GMT
--
-- Node definitions
--
--  1.3.6.1.4.1.33922.106
-- July 25, 2019 at 14:33 GMT
--
-- Node definitions
--
-- 1.3.6.1.4.1.33922
-- 1.3.6.1.4.1.33922
-- 1.3.6.1.4.1.33922
-- 1.3.6.1.4.1.33922
-- 1.3.6.1.4.1.33922
-- 1.3.6.1.4.1.33922
-- 1.3.6.1.4.1.33922
-- 1.3.6.1.4.1.33922
-- 1.3.6.1.4.1.33922
		-- 1.3.6.1.4.1.33922
		byzoro OBJECT IDENTIFIER ::= { enterprises 33922 }


--          1.3.6.1.4.1.33922.106.1
-- 1.3.6.1.4.1.33922.106.1
-- 1.3.6.1.4.1.33922.106.1
-- 1.3.6.1.4.1.33922.106.1
-- 1.3.6.1.4.1.33922.106.1
-- 1.3.6.1.4.1.33922.106.1
-- 1.3.6.1.4.1.33922.106.1
-- 1.3.6.1.4.1.33922.106.1
-- 1.3.6.1.4.1.33922.106.1
		-- 1.3.6.1.4.1.33922.106.1
		sysStatus OBJECT IDENTIFIER ::= { BYZORO-T7600 1 }


--          1.3.6.1.4.1.33922.106.1.1
-- 1.3.6.1.4.1.33922.106.1.1
-- 1.3.6.1.4.1.33922.106.1.1
-- 1.3.6.1.4.1.33922.106.1.1
-- 1.3.6.1.4.1.33922.106.1.1
-- 1.3.6.1.4.1.33922.106.1.1
-- 1.3.6.1.4.1.33922.106.1.1
-- 1.3.6.1.4.1.33922.106.1.1
-- 1.3.6.1.4.1.33922.106.1.1
		-- 1.3.6.1.4.1.33922.106.1.1
		cpuUsage OBJECT-TYPE
			SYNTAX Integer32 (0..100)
			UNITS "%"
			MAX-ACCESS read-only
			STATUS current
			DESCRIPTION
				"CPU usage (%)"
			::= { sysStatus 1 }


--          1.3.6.1.4.1.33922.106.1.2
-- 1.3.6.1.4.1.33922.106.1.2
-- 1.3.6.1.4.1.33922.106.1.2
-- 1.3.6.1.4.1.33922.106.1.2
-- 1.3.6.1.4.1.33922.106.1.2
-- 1.3.6.1.4.1.33922.106.1.2
-- 1.3.6.1.4.1.33922.106.1.2
-- 1.3.6.1.4.1.33922.106.1.2
-- 1.3.6.1.4.1.33922.106.1.2
		-- 1.3.6.1.4.1.33922.106.1.2
		memoryUsage OBJECT-TYPE
			SYNTAX Integer32 (0..100)
			UNITS "%"
			MAX-ACCESS read-only
			STATUS current
			DESCRIPTION
				"memory usage (%)"
			::= { sysStatus 2 }


--          1.3.6.1.4.1.33922.106.1.3
-- 1.3.6.1.4.1.33922.106.1.3
-- 1.3.6.1.4.1.33922.106.1.3
-- 1.3.6.1.4.1.33922.106.1.3
-- 1.3.6.1.4.1.33922.106.1.3
-- 1.3.6.1.4.1.33922.106.1.3
-- 1.3.6.1.4.1.33922.106.1.3
-- 1.3.6.1.4.1.33922.106.1.3
-- 1.3.6.1.4.1.33922.106.1.3
		-- 1.3.6.1.4.1.33922.106.1.3
		storageUsage OBJECT-TYPE
			SYNTAX Integer32 (0..100)
			UNITS "%"
			MAX-ACCESS read-only
			STATUS current
			DESCRIPTION
				"storage usage (%)"
			::= { sysStatus 3 }


--          1.3.6.1.4.1.33922.106.1.4
-- 1.3.6.1.4.1.33922.106.1.4
-- 1.3.6.1.4.1.33922.106.1.4
-- 1.3.6.1.4.1.33922.106.1.4
-- 1.3.6.1.4.1.33922.106.1.4
-- 1.3.6.1.4.1.33922.106.1.4
-- 1.3.6.1.4.1.33922.106.1.4
-- 1.3.6.1.4.1.33922.106.1.4
-- 1.3.6.1.4.1.33922.106.1.4
		-- 1.3.6.1.4.1.33922.106.1.4
		sysRunTime OBJECT-TYPE
			SYNTAX DisplayString
			UNITS "s"
			MAX-ACCESS read-only
			STATUS current
			DESCRIPTION
				" system run time from start:"
			::= { sysStatus 4 }


--          1.3.6.1.4.1.33922.106.1.5
-- 1.3.6.1.4.1.33922.106.1.5
-- 1.3.6.1.4.1.33922.106.1.5
-- 1.3.6.1.4.1.33922.106.1.5
-- 1.3.6.1.4.1.33922.106.1.5
-- 1.3.6.1.4.1.33922.106.1.5
-- 1.3.6.1.4.1.33922.106.1.5
-- 1.3.6.1.4.1.33922.106.1.5
-- 1.3.6.1.4.1.33922.106.1.5
		-- 1.3.6.1.4.1.33922.106.1.5
		powerStatusTable OBJECT-TYPE
			SYNTAX SEQUENCE OF PowerStatusEntry
			MAX-ACCESS not-accessible
			STATUS current
			DESCRIPTION
				"Description."
			::= { sysStatus 5 }


--          1.3.6.1.4.1.33922.106.1.5.1
-- 1.3.6.1.4.1.33922.106.1.5.1
-- 1.3.6.1.4.1.33922.106.1.5.1
-- 1.3.6.1.4.1.33922.106.1.5.1
-- 1.3.6.1.4.1.33922.106.1.5.1
-- 1.3.6.1.4.1.33922.106.1.5.1
-- 1.3.6.1.4.1.33922.106.1.5.1
-- 1.3.6.1.4.1.33922.106.1.5.1
-- 1.3.6.1.4.1.33922.106.1.5.1
		-- 1.3.6.1.4.1.33922.106.1.5.1
		powerStatusEntry OBJECT-TYPE
			SYNTAX PowerStatusEntry
			MAX-ACCESS not-accessible
			STATUS current
			DESCRIPTION
				"Description."
			INDEX { powerIndex }
			::= { powerStatusTable 1 }


		PowerStatusEntry ::=
			SEQUENCE {
				powerIndex
					Integer32,
				powerStaus
					INTEGER
			 }

--          1.3.6.1.4.1.33922.106.1.5.1.1
-- 1.3.6.1.4.1.33922.106.1.5.1.1
-- 1.3.6.1.4.1.33922.106.1.5.1.1
-- 1.3.6.1.4.1.33922.106.1.5.1.1
-- 1.3.6.1.4.1.33922.106.1.5.1.1
-- 1.3.6.1.4.1.33922.106.1.5.1.1
-- 1.3.6.1.4.1.33922.106.1.5.1.1
-- 1.3.6.1.4.1.33922.106.1.5.1.1
-- 1.3.6.1.4.1.33922.106.1.5.1.1
		-- 1.3.6.1.4.1.33922.106.1.5.1.1
		powerIndex OBJECT-TYPE
			SYNTAX Integer32 (0..10)
			MAX-ACCESS read-only
			STATUS current
			DESCRIPTION
				"Description."
			::= { powerStatusEntry 1 }


--          1.3.6.1.4.1.33922.106.1.5.1.2
-- 1.3.6.1.4.1.33922.106.1.5.1.2
-- 1.3.6.1.4.1.33922.106.1.5.1.2
-- 1.3.6.1.4.1.33922.106.1.5.1.2
-- 1.3.6.1.4.1.33922.106.1.5.1.2
-- 1.3.6.1.4.1.33922.106.1.5.1.2
-- 1.3.6.1.4.1.33922.106.1.5.1.2
-- 1.3.6.1.4.1.33922.106.1.5.1.2
-- 1.3.6.1.4.1.33922.106.1.5.1.2
		-- 1.3.6.1.4.1.33922.106.1.5.1.2
		powerStaus OBJECT-TYPE
			SYNTAX INTEGER
				{
				off(0),
				on(1)
				}
			MAX-ACCESS read-only
			STATUS current
			DESCRIPTION
				"Description."
			::= { powerStatusEntry 2 }


--          1.3.6.1.4.1.33922.106.1.6
-- 1.3.6.1.4.1.33922.106.1.6
-- 1.3.6.1.4.1.33922.106.1.6
-- 1.3.6.1.4.1.33922.106.1.6
-- 1.3.6.1.4.1.33922.106.1.6
-- 1.3.6.1.4.1.33922.106.1.6
-- 1.3.6.1.4.1.33922.106.1.6
-- 1.3.6.1.4.1.33922.106.1.6
-- 1.3.6.1.4.1.33922.106.1.6
		-- 1.3.6.1.4.1.33922.106.1.6
		fanSpeedTable OBJECT-TYPE
			SYNTAX SEQUENCE OF FanSpeedEntry
			MAX-ACCESS not-accessible
			STATUS current
			DESCRIPTION
				"Description."
			::= { sysStatus 6 }


--          1.3.6.1.4.1.33922.106.1.6.1
-- 1.3.6.1.4.1.33922.106.1.6.1
-- 1.3.6.1.4.1.33922.106.1.6.1
-- 1.3.6.1.4.1.33922.106.1.6.1
-- 1.3.6.1.4.1.33922.106.1.6.1
-- 1.3.6.1.4.1.33922.106.1.6.1
-- 1.3.6.1.4.1.33922.106.1.6.1
-- 1.3.6.1.4.1.33922.106.1.6.1
-- 1.3.6.1.4.1.33922.106.1.6.1
		-- 1.3.6.1.4.1.33922.106.1.6.1
		fanSpeedEntry OBJECT-TYPE
			SYNTAX FanSpeedEntry
			MAX-ACCESS not-accessible
			STATUS current
			DESCRIPTION
				"Description."
			INDEX { fanIndex }
			::= { fanSpeedTable 1 }


		FanSpeedEntry ::=
			SEQUENCE {
				fanIndex
					Integer32,
				fanStatus
					Integer32
			 }

--          1.3.6.1.4.1.33922.106.1.6.1.1
-- 1.3.6.1.4.1.33922.106.1.6.1.1
-- 1.3.6.1.4.1.33922.106.1.6.1.1
-- 1.3.6.1.4.1.33922.106.1.6.1.1
-- 1.3.6.1.4.1.33922.106.1.6.1.1
-- 1.3.6.1.4.1.33922.106.1.6.1.1
-- 1.3.6.1.4.1.33922.106.1.6.1.1
-- 1.3.6.1.4.1.33922.106.1.6.1.1
-- 1.3.6.1.4.1.33922.106.1.6.1.1
		-- 1.3.6.1.4.1.33922.106.1.6.1.1
		fanIndex OBJECT-TYPE
			SYNTAX Integer32 (0..10)
			MAX-ACCESS read-only
			STATUS current
			DESCRIPTION
				"Description."
			::= { fanSpeedEntry 1 }


--          1.3.6.1.4.1.33922.106.1.6.1.2
-- 1.3.6.1.4.1.33922.106.1.6.1.2
-- 1.3.6.1.4.1.33922.106.1.6.1.2
-- 1.3.6.1.4.1.33922.106.1.6.1.2
-- 1.3.6.1.4.1.33922.106.1.6.1.2
-- 1.3.6.1.4.1.33922.106.1.6.1.2
-- 1.3.6.1.4.1.33922.106.1.6.1.2
-- 1.3.6.1.4.1.33922.106.1.6.1.2
-- 1.3.6.1.4.1.33922.106.1.6.1.2
		-- 1.3.6.1.4.1.33922.106.1.6.1.2
		fanStatus OBJECT-TYPE
			SYNTAX Integer32
			UNITS "r/min"
			MAX-ACCESS read-only
			STATUS current
			DESCRIPTION
				"Description."
			::= { fanSpeedEntry 2 }


--          1.3.6.1.4.1.33922.106.1.7
-- 1.3.6.1.4.1.33922.106.1.7
-- 1.3.6.1.4.1.33922.106.1.7
-- 1.3.6.1.4.1.33922.106.1.7
-- 1.3.6.1.4.1.33922.106.1.7
-- 1.3.6.1.4.1.33922.106.1.7
-- 1.3.6.1.4.1.33922.106.1.7
-- 1.3.6.1.4.1.33922.106.1.7
-- 1.3.6.1.4.1.33922.106.1.7
		-- 1.3.6.1.4.1.33922.106.1.7
		temperatureTable OBJECT-TYPE
			SYNTAX SEQUENCE OF TemperatureEntry
			MAX-ACCESS not-accessible
			STATUS current
			DESCRIPTION
				"Description."
			::= { sysStatus 7 }


--          1.3.6.1.4.1.33922.106.1.7.1
-- 1.3.6.1.4.1.33922.106.1.7.1
-- 1.3.6.1.4.1.33922.106.1.7.1
-- 1.3.6.1.4.1.33922.106.1.7.1
-- 1.3.6.1.4.1.33922.106.1.7.1
-- 1.3.6.1.4.1.33922.106.1.7.1
-- 1.3.6.1.4.1.33922.106.1.7.1
-- 1.3.6.1.4.1.33922.106.1.7.1
-- 1.3.6.1.4.1.33922.106.1.7.1
		-- 1.3.6.1.4.1.33922.106.1.7.1
		temperatureEntry OBJECT-TYPE
			SYNTAX TemperatureEntry
			MAX-ACCESS not-accessible
			STATUS current
			DESCRIPTION
				"Description."
			INDEX { temperatureIndex }
			::= { temperatureTable 1 }


		TemperatureEntry ::=
			SEQUENCE {
				temperatureIndex
					Integer32,
				tempStatus
					Integer32
			 }

--          1.3.6.1.4.1.33922.106.1.7.1.1
-- 1.3.6.1.4.1.33922.106.1.7.1.1
-- 1.3.6.1.4.1.33922.106.1.7.1.1
-- 1.3.6.1.4.1.33922.106.1.7.1.1
-- 1.3.6.1.4.1.33922.106.1.7.1.1
-- 1.3.6.1.4.1.33922.106.1.7.1.1
-- 1.3.6.1.4.1.33922.106.1.7.1.1
-- 1.3.6.1.4.1.33922.106.1.7.1.1
-- 1.3.6.1.4.1.33922.106.1.7.1.1
		-- 1.3.6.1.4.1.33922.106.1.7.1.1
		temperatureIndex OBJECT-TYPE
			SYNTAX Integer32 (0..10)
			MAX-ACCESS read-only
			STATUS current
			DESCRIPTION
				"Description."
			::= { temperatureEntry 1 }


--          1.3.6.1.4.1.33922.106.1.7.1.2
-- 1.3.6.1.4.1.33922.106.1.7.1.2
-- 1.3.6.1.4.1.33922.106.1.7.1.2
-- 1.3.6.1.4.1.33922.106.1.7.1.2
-- 1.3.6.1.4.1.33922.106.1.7.1.2
-- 1.3.6.1.4.1.33922.106.1.7.1.2
-- 1.3.6.1.4.1.33922.106.1.7.1.2
-- 1.3.6.1.4.1.33922.106.1.7.1.2
-- 1.3.6.1.4.1.33922.106.1.7.1.2
		-- 1.3.6.1.4.1.33922.106.1.7.1.2
		tempStatus OBJECT-TYPE
			SYNTAX Integer32
			UNITS "C"
			MAX-ACCESS read-only
			STATUS current
			DESCRIPTION
				"Description."
			::= { temperatureEntry 2 }


--          1.3.6.1.4.1.33922.106.2
-- 1.3.6.1.4.1.33922.106.2
-- 1.3.6.1.4.1.33922.106.2
-- 1.3.6.1.4.1.33922.106.2
-- 1.3.6.1.4.1.33922.106.2
-- 1.3.6.1.4.1.33922.106.2
-- 1.3.6.1.4.1.33922.106.2
-- 1.3.6.1.4.1.33922.106.2
-- 1.3.6.1.4.1.33922.106.2
		-- 1.3.6.1.4.1.33922.106.2
		sysPara OBJECT IDENTIFIER ::= { BYZORO-T7600 2 }


--          1.3.6.1.4.1.33922.106.2.1
-- 1.3.6.1.4.1.33922.106.2.1
-- 1.3.6.1.4.1.33922.106.2.1
-- 1.3.6.1.4.1.33922.106.2.1
-- 1.3.6.1.4.1.33922.106.2.1
-- 1.3.6.1.4.1.33922.106.2.1
-- 1.3.6.1.4.1.33922.106.2.1
-- 1.3.6.1.4.1.33922.106.2.1
-- 1.3.6.1.4.1.33922.106.2.1
		-- 1.3.6.1.4.1.33922.106.2.1
		deviceName OBJECT-TYPE
			SYNTAX DisplayString (SIZE (0..30))
			MAX-ACCESS read-only
			STATUS current
			DESCRIPTION
				"system name.
				to identify the device"
			::= { sysPara 1 }


--      1.3.6.1.4.1.33922.106.2.2
-- 1.3.6.1.4.1.33922.106.2.2
-- 1.3.6.1.4.1.33922.106.2.2
-- 1.3.6.1.4.1.33922.106.2.2
-- 1.3.6.1.4.1.33922.106.2.2
		-- 1.3.6.1.4.1.33922.106.2.2
		deviceDescription OBJECT-TYPE
			SYNTAX DisplayString
			MAX-ACCESS read-write
			STATUS current
			DESCRIPTION
				"device information remasks"
			::= { sysPara 2 }


--          1.3.6.1.4.1.33922.106.2.2
-- 1.3.6.1.4.1.33922.106.2.2
-- 1.3.6.1.4.1.33922.106.2.2
-- 1.3.6.1.4.1.33922.106.2.2
-- 1.3.6.1.4.1.33922.106.2.3
-- 1.3.6.1.4.1.33922.106.2.3
-- 1.3.6.1.4.1.33922.106.2.3
-- 1.3.6.1.4.1.33922.106.2.3
-- 1.3.6.1.4.1.33922.106.2.3
		-- 1.3.6.1.4.1.33922.106.2.3
		systemLocation OBJECT-TYPE
			SYNTAX DisplayString (SIZE (0..30))
			MAX-ACCESS read-write
			STATUS current
			DESCRIPTION
				" "
			::= { sysPara 3 }


--          1.3.6.1.4.1.33922.106.2.3
-- 1.3.6.1.4.1.33922.106.2.3
-- 1.3.6.1.4.1.33922.106.2.3
-- 1.3.6.1.4.1.33922.106.2.3
-- 1.3.6.1.4.1.33922.106.2.4
-- 1.3.6.1.4.1.33922.106.2.4
-- 1.3.6.1.4.1.33922.106.2.4
-- 1.3.6.1.4.1.33922.106.2.4
-- 1.3.6.1.4.1.33922.106.2.4
		-- 1.3.6.1.4.1.33922.106.2.4
		systemContact OBJECT-TYPE
			SYNTAX DisplayString (SIZE (0..30))
			MAX-ACCESS read-write
			STATUS current
			DESCRIPTION
				" "
			::= { sysPara 4 }


--          1.3.6.1.4.1.33922.106.2.4
-- 1.3.6.1.4.1.33922.106.2.4
-- 1.3.6.1.4.1.33922.106.2.4
-- 1.3.6.1.4.1.33922.106.2.4
-- 1.3.6.1.4.1.33922.106.2.5
-- 1.3.6.1.4.1.33922.106.2.5
-- 1.3.6.1.4.1.33922.106.2.5
-- 1.3.6.1.4.1.33922.106.2.5
-- 1.3.6.1.4.1.33922.106.2.5
		-- 1.3.6.1.4.1.33922.106.2.5
		softwareVer OBJECT-TYPE
			SYNTAX DisplayString
			MAX-ACCESS read-only
			STATUS current
			DESCRIPTION
				"software version"
			::= { sysPara 5 }


--          1.3.6.1.4.1.33922.106.2.5
-- 1.3.6.1.4.1.33922.106.2.5
-- 1.3.6.1.4.1.33922.106.2.5
-- 1.3.6.1.4.1.33922.106.2.5
-- 1.3.6.1.4.1.33922.106.2.6
-- 1.3.6.1.4.1.33922.106.2.6
-- 1.3.6.1.4.1.33922.106.2.6
-- 1.3.6.1.4.1.33922.106.2.6
-- 1.3.6.1.4.1.33922.106.2.6
		-- 1.3.6.1.4.1.33922.106.2.6
		hardwareVer OBJECT-TYPE
			SYNTAX DisplayString
			MAX-ACCESS read-only
			STATUS current
			DESCRIPTION
				"hardware version"
			::= { sysPara 6 }


--          1.3.6.1.4.1.33922.106.2.6
-- 1.3.6.1.4.1.33922.106.2.6
-- 1.3.6.1.4.1.33922.106.2.6
-- 1.3.6.1.4.1.33922.106.2.6
-- 1.3.6.1.4.1.33922.106.2.7
-- 1.3.6.1.4.1.33922.106.2.7
-- 1.3.6.1.4.1.33922.106.2.7
-- 1.3.6.1.4.1.33922.106.2.7
-- 1.3.6.1.4.1.33922.106.2.7
		-- 1.3.6.1.4.1.33922.106.2.7
		modelName OBJECT-TYPE
			SYNTAX DisplayString
			MAX-ACCESS read-only
			STATUS current
			DESCRIPTION
				"model name"
			::= { sysPara 7 }


--          1.3.6.1.4.1.33922.106.2.10
-- 1.3.6.1.4.1.33922.106.2.10
-- 1.3.6.1.4.1.33922.106.2.10
-- 1.3.6.1.4.1.33922.106.2.10
-- 1.3.6.1.4.1.33922.106.2.11
-- 1.3.6.1.4.1.33922.106.2.11
-- 1.3.6.1.4.1.33922.106.2.11
-- 1.3.6.1.4.1.33922.106.2.11
-- 1.3.6.1.4.1.33922.106.2.8
		-- 1.3.6.1.4.1.33922.106.2.8
		time OBJECT IDENTIFIER ::= { sysPara 8 }


--          1.3.6.1.4.1.33922.106.2.10.1
-- 1.3.6.1.4.1.33922.106.2.10.1
-- 1.3.6.1.4.1.33922.106.2.10.1
-- 1.3.6.1.4.1.33922.106.2.10.1
-- 1.3.6.1.4.1.33922.106.2.11.1
-- 1.3.6.1.4.1.33922.106.2.11.1
-- 1.3.6.1.4.1.33922.106.2.11.1
-- 1.3.6.1.4.1.33922.106.2.11.1
-- 1.3.6.1.4.1.33922.106.2.8.1
		-- 1.3.6.1.4.1.33922.106.2.8.1
		systime OBJECT-TYPE
			SYNTAX DisplayString
			MAX-ACCESS read-write
			STATUS current
			DESCRIPTION
				" read or set system time:
				format:
				YYYY-MM-DD HH:MM:SS"
			::= { time 1 }


--          1.3.6.1.4.1.33922.106.2.10.2
-- 1.3.6.1.4.1.33922.106.2.10.2
-- 1.3.6.1.4.1.33922.106.2.10.2
-- 1.3.6.1.4.1.33922.106.2.10.2
-- 1.3.6.1.4.1.33922.106.2.11.2
-- 1.3.6.1.4.1.33922.106.2.11.2
-- 1.3.6.1.4.1.33922.106.2.11.2
-- 1.3.6.1.4.1.33922.106.2.11.2
-- 1.3.6.1.4.1.33922.106.2.8.2
		-- 1.3.6.1.4.1.33922.106.2.8.2
		timeZoneSwi OBJECT-TYPE
			SYNTAX INTEGER
				{
				on(0),
				off(1)
				}
			MAX-ACCESS read-write
			STATUS current
			DESCRIPTION
				"enable time zone"
			::= { time 2 }


--          1.3.6.1.4.1.33922.106.2.10.3
-- 1.3.6.1.4.1.33922.106.2.10.3
-- 1.3.6.1.4.1.33922.106.2.10.3
-- 1.3.6.1.4.1.33922.106.2.10.3
-- 1.3.6.1.4.1.33922.106.2.11.3
-- 1.3.6.1.4.1.33922.106.2.11.3
-- 1.3.6.1.4.1.33922.106.2.11.3
-- 1.3.6.1.4.1.33922.106.2.11.3
-- 1.3.6.1.4.1.33922.106.2.8.3
		-- 1.3.6.1.4.1.33922.106.2.8.3
		timeZone OBJECT-TYPE
			SYNTAX Integer32 (-12..12)
			MAX-ACCESS read-write
			STATUS current
			DESCRIPTION
				"read or set timezone:
				+N standfor eastern,eg:8 standfor UTC+8
				-N standfor western,eg:-8 standfor UTC-8"
			::= { time 3 }


--          1.3.6.1.4.1.33922.106.2.10.4
-- 1.3.6.1.4.1.33922.106.2.10.4
-- 1.3.6.1.4.1.33922.106.2.10.4
-- 1.3.6.1.4.1.33922.106.2.10.4
-- 1.3.6.1.4.1.33922.106.2.11.4
-- 1.3.6.1.4.1.33922.106.2.11.4
-- 1.3.6.1.4.1.33922.106.2.11.4
-- 1.3.6.1.4.1.33922.106.2.11.4
-- 1.3.6.1.4.1.33922.106.2.8.4
		-- 1.3.6.1.4.1.33922.106.2.8.4
		dstSwitch OBJECT-TYPE
			SYNTAX INTEGER
				{
				on(0),
				off(1)
				}
			MAX-ACCESS read-write
			STATUS current
			DESCRIPTION
				"enable daylight saving time"
			::= { time 4 }


--          1.3.6.1.4.1.33922.106.2.10.5
-- 1.3.6.1.4.1.33922.106.2.10.5
-- 1.3.6.1.4.1.33922.106.2.10.5
-- 1.3.6.1.4.1.33922.106.2.10.5
-- 1.3.6.1.4.1.33922.106.2.11.5
-- 1.3.6.1.4.1.33922.106.2.11.5
-- 1.3.6.1.4.1.33922.106.2.11.5
-- 1.3.6.1.4.1.33922.106.2.11.5
-- 1.3.6.1.4.1.33922.106.2.8.5
		-- 1.3.6.1.4.1.33922.106.2.8.5
		dstOffset OBJECT-TYPE
			SYNTAX Integer32
			UNITS "min"
			MAX-ACCESS read-write
			STATUS current
			DESCRIPTION
				"daylight saving time offset"
			::= { time 5 }


--  1.3.6.1.4.1.33922.106.2.8.6
		-- 1.3.6.1.4.1.33922.106.2.8.6
		dstStartTime OBJECT-TYPE
			SYNTAX DisplayString
			MAX-ACCESS read-write
			STATUS current
			DESCRIPTION
				"format:MM-DD HH:MM:SS"
			::= { time 6 }


--  format:<MM-DD> <HH:MM:SS>
-- 1.3.6.1.4.1.33922.106.2.8.7
		-- 1.3.6.1.4.1.33922.106.2.8.7
		dstEndTime OBJECT-TYPE
			SYNTAX DisplayString
			MAX-ACCESS read-write
			STATUS current
			DESCRIPTION
				"format:MM-DD HH:MM:SS"
			::= { time 7 }


--  format:<MM-DD> <HH:MM:SS>
-- 1.3.6.1.4.1.33922.106.2.11
-- 1.3.6.1.4.1.33922.106.2.11
-- 1.3.6.1.4.1.33922.106.2.11
-- 1.3.6.1.4.1.33922.106.2.11
-- 1.3.6.1.4.1.33922.106.2.12
-- 1.3.6.1.4.1.33922.106.2.12
-- 1.3.6.1.4.1.33922.106.2.12
-- 1.3.6.1.4.1.33922.106.2.12
-- 1.3.6.1.4.1.33922.106.2.9
		-- 1.3.6.1.4.1.33922.106.2.9
		networkTimeProtocol OBJECT IDENTIFIER ::= { sysPara 9 }


--          1.3.6.1.4.1.33922.106.2.11.1
-- 1.3.6.1.4.1.33922.106.2.11.1
-- 1.3.6.1.4.1.33922.106.2.11.1
-- 1.3.6.1.4.1.33922.106.2.11.1
-- 1.3.6.1.4.1.33922.106.2.12.1
-- 1.3.6.1.4.1.33922.106.2.12.1
-- 1.3.6.1.4.1.33922.106.2.12.1
-- 1.3.6.1.4.1.33922.106.2.12.1
-- 1.3.6.1.4.1.33922.106.2.9.1
		-- 1.3.6.1.4.1.33922.106.2.9.1
		ntpSwi OBJECT-TYPE
			SYNTAX INTEGER
				{
				on(0),
				off(1)
				}
			MAX-ACCESS read-write
			STATUS current
			DESCRIPTION
				"enable NTP"
			::= { networkTimeProtocol 1 }


--          1.3.6.1.4.1.33922.106.2.11.2
-- 1.3.6.1.4.1.33922.106.2.11.2
-- 1.3.6.1.4.1.33922.106.2.11.2
-- 1.3.6.1.4.1.33922.106.2.11.2
-- 1.3.6.1.4.1.33922.106.2.12.2
-- 1.3.6.1.4.1.33922.106.2.12.2
-- 1.3.6.1.4.1.33922.106.2.12.2
-- 1.3.6.1.4.1.33922.106.2.12.2
-- 1.3.6.1.4.1.33922.106.2.9.2
		-- 1.3.6.1.4.1.33922.106.2.9.2
		ntpInterval OBJECT-TYPE
			SYNTAX Integer32 (60..65535)
			MAX-ACCESS read-write
			STATUS current
			DESCRIPTION
				"the interval of NTP(second)"
			::= { networkTimeProtocol 2 }


--          1.3.6.1.4.1.33922.106.2.11.3
-- 1.3.6.1.4.1.33922.106.2.11.3
-- 1.3.6.1.4.1.33922.106.2.11.3
-- 1.3.6.1.4.1.33922.106.2.11.3
-- 1.3.6.1.4.1.33922.106.2.12.3
-- 1.3.6.1.4.1.33922.106.2.12.3
-- 1.3.6.1.4.1.33922.106.2.12.3
-- 1.3.6.1.4.1.33922.106.2.12.3
-- 1.3.6.1.4.1.33922.106.2.9.3
		-- 1.3.6.1.4.1.33922.106.2.9.3
		ntpServer1 OBJECT-TYPE
			SYNTAX DisplayString
			MAX-ACCESS read-write
			STATUS current
			DESCRIPTION
				"NTP Server1 IP"
			::= { networkTimeProtocol 3 }


--          1.3.6.1.4.1.33922.106.2.11.4
-- 1.3.6.1.4.1.33922.106.2.11.4
-- 1.3.6.1.4.1.33922.106.2.11.4
-- 1.3.6.1.4.1.33922.106.2.11.4
-- 1.3.6.1.4.1.33922.106.2.12.4
-- 1.3.6.1.4.1.33922.106.2.12.4
-- 1.3.6.1.4.1.33922.106.2.12.4
-- 1.3.6.1.4.1.33922.106.2.12.4
-- 1.3.6.1.4.1.33922.106.2.9.4
		-- 1.3.6.1.4.1.33922.106.2.9.4
		ntpServer2 OBJECT-TYPE
			SYNTAX DisplayString
			MAX-ACCESS read-write
			STATUS current
			DESCRIPTION
				"NTP Server2 IP"
			::= { networkTimeProtocol 4 }


--          1.3.6.1.4.1.33922.106.2.12
-- 1.3.6.1.4.1.33922.106.2.12
-- 1.3.6.1.4.1.33922.106.2.12
-- 1.3.6.1.4.1.33922.106.2.12
-- 1.3.6.1.4.1.33922.106.2.13
-- 1.3.6.1.4.1.33922.106.2.13
-- 1.3.6.1.4.1.33922.106.2.13
-- 1.3.6.1.4.1.33922.106.2.13
-- 1.3.6.1.4.1.33922.106.2.10
		-- 1.3.6.1.4.1.33922.106.2.10
		network OBJECT IDENTIFIER ::= { sysPara 10 }


--          1.3.6.1.4.1.33922.106.2.12.1
-- 1.3.6.1.4.1.33922.106.2.12.1
-- 1.3.6.1.4.1.33922.106.2.12.1
-- 1.3.6.1.4.1.33922.106.2.12.1
-- 1.3.6.1.4.1.33922.106.2.13.1
-- 1.3.6.1.4.1.33922.106.2.13.1
-- 1.3.6.1.4.1.33922.106.2.13.1
-- 1.3.6.1.4.1.33922.106.2.13.1
-- 1.3.6.1.4.1.33922.106.2.10.1
		-- 1.3.6.1.4.1.33922.106.2.10.1
		networkShow OBJECT IDENTIFIER ::= { network 1 }


--          1.3.6.1.4.1.33922.106.2.12.1.1
-- 1.3.6.1.4.1.33922.106.2.12.1.1
-- 1.3.6.1.4.1.33922.106.2.12.1.1
-- 1.3.6.1.4.1.33922.106.2.12.1.1
-- 1.3.6.1.4.1.33922.106.2.13.1.1
-- 1.3.6.1.4.1.33922.106.2.13.1.1
-- 1.3.6.1.4.1.33922.106.2.13.1.1
-- 1.3.6.1.4.1.33922.106.2.13.1.1
-- 1.3.6.1.4.1.33922.106.2.10.1.1
		-- 1.3.6.1.4.1.33922.106.2.10.1.1
		eth1MAC OBJECT-TYPE
			SYNTAX DisplayString
			MAX-ACCESS read-only
			STATUS current
			DESCRIPTION
				"Description."
			::= { networkShow 1 }


--          1.3.6.1.4.1.33922.106.2.12.1.2
-- 1.3.6.1.4.1.33922.106.2.12.1.2
-- 1.3.6.1.4.1.33922.106.2.12.1.2
-- 1.3.6.1.4.1.33922.106.2.12.1.2
-- 1.3.6.1.4.1.33922.106.2.13.1.2
-- 1.3.6.1.4.1.33922.106.2.13.1.2
-- 1.3.6.1.4.1.33922.106.2.13.1.2
-- 1.3.6.1.4.1.33922.106.2.13.1.2
-- 1.3.6.1.4.1.33922.106.2.10.1.2
		-- 1.3.6.1.4.1.33922.106.2.10.1.2
		eth1IPv4 OBJECT-TYPE
			SYNTAX DisplayString
			MAX-ACCESS read-write
			STATUS current
			DESCRIPTION
				"Description."
			::= { networkShow 2 }


--          1.3.6.1.4.1.33922.106.2.12.1.3
-- 1.3.6.1.4.1.33922.106.2.12.1.3
-- 1.3.6.1.4.1.33922.106.2.12.1.3
-- 1.3.6.1.4.1.33922.106.2.12.1.3
-- 1.3.6.1.4.1.33922.106.2.13.1.3
-- 1.3.6.1.4.1.33922.106.2.13.1.3
-- 1.3.6.1.4.1.33922.106.2.13.1.3
-- 1.3.6.1.4.1.33922.106.2.13.1.3
-- 1.3.6.1.4.1.33922.106.2.10.1.3
		-- 1.3.6.1.4.1.33922.106.2.10.1.3
		eth1IPv4Mask OBJECT-TYPE
			SYNTAX DisplayString
			MAX-ACCESS read-write
			STATUS current
			DESCRIPTION
				"Description."
			::= { networkShow 3 }


--          1.3.6.1.4.1.33922.106.2.12.1.4
-- 1.3.6.1.4.1.33922.106.2.12.1.4
-- 1.3.6.1.4.1.33922.106.2.12.1.4
-- 1.3.6.1.4.1.33922.106.2.12.1.4
-- 1.3.6.1.4.1.33922.106.2.13.1.4
-- 1.3.6.1.4.1.33922.106.2.13.1.4
-- 1.3.6.1.4.1.33922.106.2.13.1.4
-- 1.3.6.1.4.1.33922.106.2.13.1.4
-- 1.3.6.1.4.1.33922.106.2.10.1.4
		-- 1.3.6.1.4.1.33922.106.2.10.1.4
		eth1IPv6 OBJECT-TYPE
			SYNTAX DisplayString
			MAX-ACCESS read-write
			STATUS current
			DESCRIPTION
				"Description."
			::= { networkShow 4 }


--          1.3.6.1.4.1.33922.106.2.12.1.5
-- 1.3.6.1.4.1.33922.106.2.12.1.5
-- 1.3.6.1.4.1.33922.106.2.12.1.5
-- 1.3.6.1.4.1.33922.106.2.12.1.5
-- 1.3.6.1.4.1.33922.106.2.13.1.5
-- 1.3.6.1.4.1.33922.106.2.13.1.5
-- 1.3.6.1.4.1.33922.106.2.13.1.5
-- 1.3.6.1.4.1.33922.106.2.13.1.5
-- 1.3.6.1.4.1.33922.106.2.10.1.5
		-- 1.3.6.1.4.1.33922.106.2.10.1.5
		eth2MAC OBJECT-TYPE
			SYNTAX DisplayString
			MAX-ACCESS read-only
			STATUS current
			DESCRIPTION
				"Description."
			::= { networkShow 5 }


--          1.3.6.1.4.1.33922.106.2.12.1.6
-- 1.3.6.1.4.1.33922.106.2.12.1.6
-- 1.3.6.1.4.1.33922.106.2.12.1.6
-- 1.3.6.1.4.1.33922.106.2.12.1.6
-- 1.3.6.1.4.1.33922.106.2.13.1.6
-- 1.3.6.1.4.1.33922.106.2.13.1.6
-- 1.3.6.1.4.1.33922.106.2.13.1.6
-- 1.3.6.1.4.1.33922.106.2.13.1.6
-- 1.3.6.1.4.1.33922.106.2.10.1.6
		-- 1.3.6.1.4.1.33922.106.2.10.1.6
		eth2IPv4 OBJECT-TYPE
			SYNTAX DisplayString
			MAX-ACCESS read-write
			STATUS current
			DESCRIPTION
				"Description."
			::= { networkShow 6 }


--          1.3.6.1.4.1.33922.106.2.12.1.7
-- 1.3.6.1.4.1.33922.106.2.12.1.7
-- 1.3.6.1.4.1.33922.106.2.12.1.7
-- 1.3.6.1.4.1.33922.106.2.12.1.7
-- 1.3.6.1.4.1.33922.106.2.13.1.7
-- 1.3.6.1.4.1.33922.106.2.13.1.7
-- 1.3.6.1.4.1.33922.106.2.13.1.7
-- 1.3.6.1.4.1.33922.106.2.13.1.7
-- 1.3.6.1.4.1.33922.106.2.10.1.7
		-- 1.3.6.1.4.1.33922.106.2.10.1.7
		eth2IPv4Mask OBJECT-TYPE
			SYNTAX DisplayString
			MAX-ACCESS read-write
			STATUS current
			DESCRIPTION
				"Description."
			::= { networkShow 7 }


--          1.3.6.1.4.1.33922.106.2.12.1.8
-- 1.3.6.1.4.1.33922.106.2.12.1.8
-- 1.3.6.1.4.1.33922.106.2.12.1.8
-- 1.3.6.1.4.1.33922.106.2.12.1.8
-- 1.3.6.1.4.1.33922.106.2.13.1.8
-- 1.3.6.1.4.1.33922.106.2.13.1.8
-- 1.3.6.1.4.1.33922.106.2.13.1.8
-- 1.3.6.1.4.1.33922.106.2.13.1.8
-- 1.3.6.1.4.1.33922.106.2.10.1.8
		-- 1.3.6.1.4.1.33922.106.2.10.1.8
		eth2IPv6 OBJECT-TYPE
			SYNTAX DisplayString
			MAX-ACCESS read-write
			STATUS current
			DESCRIPTION
				"Description."
			::= { networkShow 8 }


--          1.3.6.1.4.1.33922.106.2.12.3
-- 1.3.6.1.4.1.33922.106.2.12.3
-- 1.3.6.1.4.1.33922.106.2.12.3
-- 1.3.6.1.4.1.33922.106.2.12.3
-- 1.3.6.1.4.1.33922.106.2.13.2
-- 1.3.6.1.4.1.33922.106.2.13.2
-- 1.3.6.1.4.1.33922.106.2.13.2
-- 1.3.6.1.4.1.33922.106.2.13.2
-- 1.3.6.1.4.1.33922.106.2.10.2
		-- 1.3.6.1.4.1.33922.106.2.10.2
		routeShow OBJECT IDENTIFIER ::= { network 2 }


--          1.3.6.1.4.1.33922.106.2.12.3.1
-- 1.3.6.1.4.1.33922.106.2.12.3.1
-- 1.3.6.1.4.1.33922.106.2.12.3.1
-- 1.3.6.1.4.1.33922.106.2.12.3.1
-- 1.3.6.1.4.1.33922.106.2.13.2.1
-- 1.3.6.1.4.1.33922.106.2.13.2.1
-- 1.3.6.1.4.1.33922.106.2.13.2.1
-- 1.3.6.1.4.1.33922.106.2.13.2.1
-- 1.3.6.1.4.1.33922.106.2.10.2.1
		-- 1.3.6.1.4.1.33922.106.2.10.2.1
		ipv4RouteTable OBJECT-TYPE
			SYNTAX SEQUENCE OF Ipv4RouteEntry
			MAX-ACCESS not-accessible
			STATUS current
			DESCRIPTION
				"Description."
			::= { routeShow 1 }


--          1.3.6.1.4.1.33922.106.2.12.3.1.1
-- 1.3.6.1.4.1.33922.106.2.12.3.1.1
-- 1.3.6.1.4.1.33922.106.2.12.3.1.1
-- 1.3.6.1.4.1.33922.106.2.12.3.1.1
-- 1.3.6.1.4.1.33922.106.2.13.2.1.1
-- 1.3.6.1.4.1.33922.106.2.13.2.1.1
-- 1.3.6.1.4.1.33922.106.2.13.2.1.1
-- 1.3.6.1.4.1.33922.106.2.13.2.1.1
-- 1.3.6.1.4.1.33922.106.2.10.2.1.1
		-- 1.3.6.1.4.1.33922.106.2.10.2.1.1
		ipv4RouteEntry OBJECT-TYPE
			SYNTAX Ipv4RouteEntry
			MAX-ACCESS not-accessible
			STATUS current
			DESCRIPTION
				"Description."
			INDEX { ipv4RouteIndex }
			::= { ipv4RouteTable 1 }


		Ipv4RouteEntry ::=
			SEQUENCE {
				ipv4RouteIndex
					Integer32,
				ipv4RouteDip
					DisplayString,
				ipv4RouteMask
					DisplayString,
				ipv4RouteGateway
					DisplayString,
				ipv4RouteInterface
					DisplayString,
				ipv4RouteValid
					INTEGER
			 }

--          1.3.6.1.4.1.33922.106.2.12.3.1.1.1
-- 1.3.6.1.4.1.33922.106.2.12.3.1.1.1
-- 1.3.6.1.4.1.33922.106.2.12.3.1.1.1
-- 1.3.6.1.4.1.33922.106.2.12.3.1.1.1
-- 1.3.6.1.4.1.33922.106.2.13.2.1.1.1
-- 1.3.6.1.4.1.33922.106.2.13.2.1.1.1
-- 1.3.6.1.4.1.33922.106.2.13.2.1.1.1
-- 1.3.6.1.4.1.33922.106.2.13.2.1.1.1
-- 1.3.6.1.4.1.33922.106.2.10.2.1.1.1
		-- 1.3.6.1.4.1.33922.106.2.10.2.1.1.1
		ipv4RouteIndex OBJECT-TYPE
			SYNTAX Integer32 (0..5)
			MAX-ACCESS read-only
			STATUS current
			DESCRIPTION
				"Description."
			::= { ipv4RouteEntry 1 }


--          1.3.6.1.4.1.33922.106.2.12.3.1.1.2
-- 1.3.6.1.4.1.33922.106.2.12.3.1.1.2
-- 1.3.6.1.4.1.33922.106.2.12.3.1.1.2
-- 1.3.6.1.4.1.33922.106.2.12.3.1.1.2
-- 1.3.6.1.4.1.33922.106.2.13.2.1.1.2
-- 1.3.6.1.4.1.33922.106.2.13.2.1.1.2
-- 1.3.6.1.4.1.33922.106.2.13.2.1.1.2
-- 1.3.6.1.4.1.33922.106.2.13.2.1.1.2
-- 1.3.6.1.4.1.33922.106.2.10.2.1.1.2
		-- 1.3.6.1.4.1.33922.106.2.10.2.1.1.2
		ipv4RouteDip OBJECT-TYPE
			SYNTAX DisplayString
			MAX-ACCESS read-only
			STATUS current
			DESCRIPTION
				"Description."
			::= { ipv4RouteEntry 2 }


--           destination ip segment
--
-- 1.3.6.1.4.1.33922.106.2.12.3.1.1.3
-- 1.3.6.1.4.1.33922.106.2.12.3.1.1.3
-- 1.3.6.1.4.1.33922.106.2.12.3.1.1.3
-- 1.3.6.1.4.1.33922.106.2.12.3.1.1.3
-- 1.3.6.1.4.1.33922.106.2.13.2.1.1.3
-- 1.3.6.1.4.1.33922.106.2.13.2.1.1.3
-- 1.3.6.1.4.1.33922.106.2.13.2.1.1.3
-- 1.3.6.1.4.1.33922.106.2.13.2.1.1.3
-- 1.3.6.1.4.1.33922.106.2.10.2.1.1.3
		-- 1.3.6.1.4.1.33922.106.2.10.2.1.1.3
		ipv4RouteMask OBJECT-TYPE
			SYNTAX DisplayString
			MAX-ACCESS read-only
			STATUS current
			DESCRIPTION
				"Description."
			::= { ipv4RouteEntry 3 }


--          1.3.6.1.4.1.33922.106.2.12.3.1.1.4
-- 1.3.6.1.4.1.33922.106.2.12.3.1.1.4
-- 1.3.6.1.4.1.33922.106.2.12.3.1.1.4
-- 1.3.6.1.4.1.33922.106.2.12.3.1.1.4
-- 1.3.6.1.4.1.33922.106.2.13.2.1.1.4
-- 1.3.6.1.4.1.33922.106.2.13.2.1.1.4
-- 1.3.6.1.4.1.33922.106.2.13.2.1.1.4
-- 1.3.6.1.4.1.33922.106.2.13.2.1.1.4
-- 1.3.6.1.4.1.33922.106.2.10.2.1.1.4
		-- 1.3.6.1.4.1.33922.106.2.10.2.1.1.4
		ipv4RouteGateway OBJECT-TYPE
			SYNTAX DisplayString
			MAX-ACCESS read-only
			STATUS current
			DESCRIPTION
				"Description."
			::= { ipv4RouteEntry 4 }


--          1.3.6.1.4.1.33922.106.2.12.3.1.1.5
-- 1.3.6.1.4.1.33922.106.2.12.3.1.1.5
-- 1.3.6.1.4.1.33922.106.2.12.3.1.1.5
-- 1.3.6.1.4.1.33922.106.2.12.3.1.1.5
-- 1.3.6.1.4.1.33922.106.2.13.2.1.1.5
-- 1.3.6.1.4.1.33922.106.2.13.2.1.1.5
-- 1.3.6.1.4.1.33922.106.2.13.2.1.1.5
-- 1.3.6.1.4.1.33922.106.2.13.2.1.1.5
-- 1.3.6.1.4.1.33922.106.2.10.2.1.1.5
		-- 1.3.6.1.4.1.33922.106.2.10.2.1.1.5
		ipv4RouteInterface OBJECT-TYPE
			SYNTAX DisplayString
			MAX-ACCESS read-only
			STATUS current
			DESCRIPTION
				" eth1 or eth2
				"
			::= { ipv4RouteEntry 5 }


--
--
-- 1.3.6.1.4.1.33922.106.2.12.3.1.1.6
-- 1.3.6.1.4.1.33922.106.2.12.3.1.1.6
-- 1.3.6.1.4.1.33922.106.2.12.3.1.1.6
-- 1.3.6.1.4.1.33922.106.2.12.3.1.1.6
-- 1.3.6.1.4.1.33922.106.2.13.2.1.1.6
-- 1.3.6.1.4.1.33922.106.2.13.2.1.1.6
-- 1.3.6.1.4.1.33922.106.2.13.2.1.1.6
-- 1.3.6.1.4.1.33922.106.2.13.2.1.1.6
-- 1.3.6.1.4.1.33922.106.2.10.2.1.1.6
		-- 1.3.6.1.4.1.33922.106.2.10.2.1.1.6
		ipv4RouteValid OBJECT-TYPE
			SYNTAX INTEGER
				{
				no(0),
				yes(1)
				}
			MAX-ACCESS read-only
			STATUS current
			DESCRIPTION
				"Description."
			::= { ipv4RouteEntry 6 }


--          1.3.6.1.4.1.33922.106.2.12.3.2
-- 1.3.6.1.4.1.33922.106.2.12.3.2
-- 1.3.6.1.4.1.33922.106.2.12.3.2
-- 1.3.6.1.4.1.33922.106.2.12.3.2
-- 1.3.6.1.4.1.33922.106.2.13.2.2
-- 1.3.6.1.4.1.33922.106.2.13.2.2
-- 1.3.6.1.4.1.33922.106.2.13.2.2
-- 1.3.6.1.4.1.33922.106.2.13.2.2
-- 1.3.6.1.4.1.33922.106.2.10.2.2
		-- 1.3.6.1.4.1.33922.106.2.10.2.2
		ipv6RouteTable OBJECT-TYPE
			SYNTAX SEQUENCE OF Ipv6RouteEntry
			MAX-ACCESS not-accessible
			STATUS current
			DESCRIPTION
				"Description."
			::= { routeShow 2 }


--          1.3.6.1.4.1.33922.106.2.12.3.2.1
-- 1.3.6.1.4.1.33922.106.2.12.3.2.1
-- 1.3.6.1.4.1.33922.106.2.12.3.2.1
-- 1.3.6.1.4.1.33922.106.2.12.3.2.1
-- 1.3.6.1.4.1.33922.106.2.13.2.2.1
-- 1.3.6.1.4.1.33922.106.2.13.2.2.1
-- 1.3.6.1.4.1.33922.106.2.13.2.2.1
-- 1.3.6.1.4.1.33922.106.2.13.2.2.1
-- 1.3.6.1.4.1.33922.106.2.10.2.2.1
		-- 1.3.6.1.4.1.33922.106.2.10.2.2.1
		ipv6RouteEntry OBJECT-TYPE
			SYNTAX Ipv6RouteEntry
			MAX-ACCESS not-accessible
			STATUS current
			DESCRIPTION
				"Description."
			INDEX { ipv6RouteIndex }
			::= { ipv6RouteTable 1 }


		Ipv6RouteEntry ::=
			SEQUENCE {
				ipv6RouteIndex
					Integer32,
				ipv6RouteDip
					DisplayString,
				ipv6RoutePrefixLen
					Integer32,
				ipv6RouteGateway
					DisplayString,
				ipv6RouteInterface
					DisplayString,
				ipv6RouteValid
					INTEGER
			 }

--          1.3.6.1.4.1.33922.106.2.12.3.2.1.1
-- 1.3.6.1.4.1.33922.106.2.12.3.2.1.1
-- 1.3.6.1.4.1.33922.106.2.12.3.2.1.1
-- 1.3.6.1.4.1.33922.106.2.12.3.2.1.1
-- 1.3.6.1.4.1.33922.106.2.13.2.2.1.1
-- 1.3.6.1.4.1.33922.106.2.13.2.2.1.1
-- 1.3.6.1.4.1.33922.106.2.13.2.2.1.1
-- 1.3.6.1.4.1.33922.106.2.13.2.2.1.1
-- 1.3.6.1.4.1.33922.106.2.10.2.2.1.1
		-- 1.3.6.1.4.1.33922.106.2.10.2.2.1.1
		ipv6RouteIndex OBJECT-TYPE
			SYNTAX Integer32 (0..5)
			MAX-ACCESS read-only
			STATUS current
			DESCRIPTION
				"Description."
			::= { ipv6RouteEntry 1 }


--          1.3.6.1.4.1.33922.106.2.12.3.2.1.2
-- 1.3.6.1.4.1.33922.106.2.12.3.2.1.2
-- 1.3.6.1.4.1.33922.106.2.12.3.2.1.2
-- 1.3.6.1.4.1.33922.106.2.12.3.2.1.2
-- 1.3.6.1.4.1.33922.106.2.13.2.2.1.2
-- 1.3.6.1.4.1.33922.106.2.13.2.2.1.2
-- 1.3.6.1.4.1.33922.106.2.13.2.2.1.2
-- 1.3.6.1.4.1.33922.106.2.13.2.2.1.2
-- 1.3.6.1.4.1.33922.106.2.10.2.2.1.2
		-- 1.3.6.1.4.1.33922.106.2.10.2.2.1.2
		ipv6RouteDip OBJECT-TYPE
			SYNTAX DisplayString
			MAX-ACCESS read-only
			STATUS current
			DESCRIPTION
				"Description."
			::= { ipv6RouteEntry 2 }


--          1.3.6.1.4.1.33922.106.2.12.3.2.1.3
-- 1.3.6.1.4.1.33922.106.2.12.3.2.1.3
-- 1.3.6.1.4.1.33922.106.2.12.3.2.1.3
-- 1.3.6.1.4.1.33922.106.2.12.3.2.1.3
-- 1.3.6.1.4.1.33922.106.2.13.2.2.1.3
-- 1.3.6.1.4.1.33922.106.2.13.2.2.1.3
-- 1.3.6.1.4.1.33922.106.2.13.2.2.1.3
-- 1.3.6.1.4.1.33922.106.2.13.2.2.1.3
-- 1.3.6.1.4.1.33922.106.2.10.2.2.1.3
		-- 1.3.6.1.4.1.33922.106.2.10.2.2.1.3
		ipv6RoutePrefixLen OBJECT-TYPE
			SYNTAX Integer32 (0..128)
			MAX-ACCESS read-only
			STATUS current
			DESCRIPTION
				"Description."
			::= { ipv6RouteEntry 3 }


--          1.3.6.1.4.1.33922.106.2.12.3.2.1.4
-- 1.3.6.1.4.1.33922.106.2.12.3.2.1.4
-- 1.3.6.1.4.1.33922.106.2.12.3.2.1.4
-- 1.3.6.1.4.1.33922.106.2.12.3.2.1.4
-- 1.3.6.1.4.1.33922.106.2.13.2.2.1.4
-- 1.3.6.1.4.1.33922.106.2.13.2.2.1.4
-- 1.3.6.1.4.1.33922.106.2.13.2.2.1.4
-- 1.3.6.1.4.1.33922.106.2.13.2.2.1.4
-- 1.3.6.1.4.1.33922.106.2.10.2.2.1.4
		-- 1.3.6.1.4.1.33922.106.2.10.2.2.1.4
		ipv6RouteGateway OBJECT-TYPE
			SYNTAX DisplayString
			MAX-ACCESS read-only
			STATUS current
			DESCRIPTION
				"Description."
			::= { ipv6RouteEntry 4 }


--          1.3.6.1.4.1.33922.106.2.12.3.2.1.5
-- 1.3.6.1.4.1.33922.106.2.12.3.2.1.5
-- 1.3.6.1.4.1.33922.106.2.12.3.2.1.5
-- 1.3.6.1.4.1.33922.106.2.12.3.2.1.5
-- 1.3.6.1.4.1.33922.106.2.13.2.2.1.5
-- 1.3.6.1.4.1.33922.106.2.13.2.2.1.5
-- 1.3.6.1.4.1.33922.106.2.13.2.2.1.5
-- 1.3.6.1.4.1.33922.106.2.13.2.2.1.5
-- 1.3.6.1.4.1.33922.106.2.10.2.2.1.5
		-- 1.3.6.1.4.1.33922.106.2.10.2.2.1.5
		ipv6RouteInterface OBJECT-TYPE
			SYNTAX DisplayString
			MAX-ACCESS read-only
			STATUS current
			DESCRIPTION
				"Description."
			::= { ipv6RouteEntry 5 }


--          1.3.6.1.4.1.33922.106.2.12.3.2.1.6
-- 1.3.6.1.4.1.33922.106.2.12.3.2.1.6
-- 1.3.6.1.4.1.33922.106.2.12.3.2.1.6
-- 1.3.6.1.4.1.33922.106.2.12.3.2.1.6
-- 1.3.6.1.4.1.33922.106.2.13.2.2.1.6
-- 1.3.6.1.4.1.33922.106.2.13.2.2.1.6
-- 1.3.6.1.4.1.33922.106.2.13.2.2.1.6
-- 1.3.6.1.4.1.33922.106.2.13.2.2.1.6
-- 1.3.6.1.4.1.33922.106.2.10.2.2.1.6
		-- 1.3.6.1.4.1.33922.106.2.10.2.2.1.6
		ipv6RouteValid OBJECT-TYPE
			SYNTAX INTEGER
				{
				no(0),
				yes(1)
				}
			MAX-ACCESS read-only
			STATUS current
			DESCRIPTION
				"Description."
			::= { ipv6RouteEntry 6 }


		-- 1.3.6.1.4.1.33922.106.2.11
		serialNumber OBJECT-TYPE
			SYNTAX DisplayString
			MAX-ACCESS read-only
			STATUS current
			DESCRIPTION
				"Description."
			::= { sysPara 11 }


--          1.3.6.1.4.1.33922.106.3
-- 1.3.6.1.4.1.33922.106.3
-- 1.3.6.1.4.1.33922.106.3
-- 1.3.6.1.4.1.33922.106.3
-- 1.3.6.1.4.1.33922.106.3
-- 1.3.6.1.4.1.33922.106.3
-- 1.3.6.1.4.1.33922.106.3
-- 1.3.6.1.4.1.33922.106.3
-- 1.3.6.1.4.1.33922.106.3
		-- 1.3.6.1.4.1.33922.106.3
		alarmPara OBJECT IDENTIFIER ::= { BYZORO-T7600 3 }


--          1.3.6.1.4.1.33922.106.3.1
-- 1.3.6.1.4.1.33922.106.3.1
-- 1.3.6.1.4.1.33922.106.3.1
-- 1.3.6.1.4.1.33922.106.3.1
-- 1.3.6.1.4.1.33922.106.3.1
-- 1.3.6.1.4.1.33922.106.3.1
-- 1.3.6.1.4.1.33922.106.3.1
-- 1.3.6.1.4.1.33922.106.3.1
-- 1.3.6.1.4.1.33922.106.3.1
		-- 1.3.6.1.4.1.33922.106.3.1
		cpuAlarmThreshold OBJECT-TYPE
			SYNTAX Integer32 (70..100)
			UNITS "%"
			MAX-ACCESS read-write
			STATUS current
			DESCRIPTION
				"CPU alarm threshold (%)"
			::= { alarmPara 1 }


--          1.3.6.1.4.1.33922.106.3.2
-- 1.3.6.1.4.1.33922.106.3.2
-- 1.3.6.1.4.1.33922.106.3.2
-- 1.3.6.1.4.1.33922.106.3.2
-- 1.3.6.1.4.1.33922.106.3.2
-- 1.3.6.1.4.1.33922.106.3.2
-- 1.3.6.1.4.1.33922.106.3.2
-- 1.3.6.1.4.1.33922.106.3.2
-- 1.3.6.1.4.1.33922.106.3.2
		-- 1.3.6.1.4.1.33922.106.3.2
		memAlarmThreshold OBJECT-TYPE
			SYNTAX Integer32 (70..100)
			UNITS "%"
			MAX-ACCESS read-write
			STATUS current
			DESCRIPTION
				"memory alarm threshold (%)"
			::= { alarmPara 2 }


--          1.3.6.1.4.1.33922.106.3.3
-- 1.3.6.1.4.1.33922.106.3.3
-- 1.3.6.1.4.1.33922.106.3.3
-- 1.3.6.1.4.1.33922.106.3.3
-- 1.3.6.1.4.1.33922.106.3.3
-- 1.3.6.1.4.1.33922.106.3.3
-- 1.3.6.1.4.1.33922.106.3.3
-- 1.3.6.1.4.1.33922.106.3.3
-- 1.3.6.1.4.1.33922.106.3.3
		-- 1.3.6.1.4.1.33922.106.3.3
		storageAlarmThreshold OBJECT-TYPE
			SYNTAX Integer32 (70..100)
			UNITS "%"
			MAX-ACCESS read-write
			STATUS current
			DESCRIPTION
				"storage alarm threshold (%)"
			::= { alarmPara 3 }


--          1.3.6.1.4.1.33922.106.3.4
-- 1.3.6.1.4.1.33922.106.3.4
-- 1.3.6.1.4.1.33922.106.3.4
-- 1.3.6.1.4.1.33922.106.3.4
-- 1.3.6.1.4.1.33922.106.3.4
-- 1.3.6.1.4.1.33922.106.3.4
-- 1.3.6.1.4.1.33922.106.3.4
-- 1.3.6.1.4.1.33922.106.3.4
-- 1.3.6.1.4.1.33922.106.3.4
		-- 1.3.6.1.4.1.33922.106.3.4
		portUtilizationAlarmThreshold OBJECT-TYPE
			SYNTAX Integer32 (70..100)
			UNITS "%"
			MAX-ACCESS read-write
			STATUS current
			DESCRIPTION
				"port bandwidth threshold (%)"
			::= { alarmPara 4 }


--          1.3.6.1.4.1.33922.106.3.5
-- 1.3.6.1.4.1.33922.106.3.5
-- 1.3.6.1.4.1.33922.106.3.5
-- 1.3.6.1.4.1.33922.106.3.5
-- 1.3.6.1.4.1.33922.106.3.5
-- 1.3.6.1.4.1.33922.106.3.5
-- 1.3.6.1.4.1.33922.106.3.5
-- 1.3.6.1.4.1.33922.106.3.5
-- 1.3.6.1.4.1.33922.106.3.5
		-- 1.3.6.1.4.1.33922.106.3.5
		temperatureAlarmThreshold OBJECT-TYPE
			SYNTAX Integer32 (40..90)
			UNITS "C/F"
			MAX-ACCESS read-write
			STATUS current
			DESCRIPTION
				"temperature alarm threshold ((��C))"
			::= { alarmPara 5 }


--          1.3.6.1.4.1.33922.106.3.6
-- 1.3.6.1.4.1.33922.106.3.6
-- 1.3.6.1.4.1.33922.106.3.6
-- 1.3.6.1.4.1.33922.106.3.6
-- 1.3.6.1.4.1.33922.106.3.6
-- 1.3.6.1.4.1.33922.106.3.6
-- 1.3.6.1.4.1.33922.106.3.6
-- 1.3.6.1.4.1.33922.106.3.6
-- 1.3.6.1.4.1.33922.106.3.6
		-- 1.3.6.1.4.1.33922.106.3.6
		fanLowAlarmThreshold OBJECT-TYPE
			SYNTAX Integer32 (1000..20000)
			MAX-ACCESS read-write
			STATUS current
			DESCRIPTION
				" define fan low speed alarm threshold"
			::= { alarmPara 6 }


--
--
-- 1.3.6.1.4.1.33922.106.3.7
-- 1.3.6.1.4.1.33922.106.3.7
-- 1.3.6.1.4.1.33922.106.3.7
-- 1.3.6.1.4.1.33922.106.3.7
-- 1.3.6.1.4.1.33922.106.3.7
-- 1.3.6.1.4.1.33922.106.3.7
-- 1.3.6.1.4.1.33922.106.3.7
-- 1.3.6.1.4.1.33922.106.3.7
-- 1.3.6.1.4.1.33922.106.3.7
		-- 1.3.6.1.4.1.33922.106.3.7
		fanHighAlarmThreshold OBJECT-TYPE
			SYNTAX Integer32 (1000..23000)
			MAX-ACCESS read-write
			STATUS current
			DESCRIPTION
				" define fan high speed alarm threshold"
			::= { alarmPara 7 }


--          1.3.6.1.4.1.33922.106.4
-- 1.3.6.1.4.1.33922.106.4
-- 1.3.6.1.4.1.33922.106.4
-- 1.3.6.1.4.1.33922.106.4
-- 1.3.6.1.4.1.33922.106.4
-- 1.3.6.1.4.1.33922.106.4
-- 1.3.6.1.4.1.33922.106.4
-- 1.3.6.1.4.1.33922.106.4
-- 1.3.6.1.4.1.33922.106.4
		-- 1.3.6.1.4.1.33922.106.4
		portPara OBJECT IDENTIFIER ::= { BYZORO-T7600 4 }


--          1.3.6.1.4.1.33922.106.4.1
-- 1.3.6.1.4.1.33922.106.4.1
-- 1.3.6.1.4.1.33922.106.4.1
-- 1.3.6.1.4.1.33922.106.4.1
-- 1.3.6.1.4.1.33922.106.4.1
-- 1.3.6.1.4.1.33922.106.4.1
-- 1.3.6.1.4.1.33922.106.4.1
-- 1.3.6.1.4.1.33922.106.4.1
-- 1.3.6.1.4.1.33922.106.4.1
		-- 1.3.6.1.4.1.33922.106.4.1
		opticalPortCount OBJECT-TYPE
			SYNTAX Integer32
			MAX-ACCESS read-only
			STATUS current
			DESCRIPTION
				"optical port numbers"
			::= { portPara 1 }


--          1.3.6.1.4.1.33922.106.4.2
-- 1.3.6.1.4.1.33922.106.4.2
-- 1.3.6.1.4.1.33922.106.4.2
-- 1.3.6.1.4.1.33922.106.4.2
-- 1.3.6.1.4.1.33922.106.4.2
-- 1.3.6.1.4.1.33922.106.4.2
-- 1.3.6.1.4.1.33922.106.4.2
-- 1.3.6.1.4.1.33922.106.4.2
-- 1.3.6.1.4.1.33922.106.4.2
		-- 1.3.6.1.4.1.33922.106.4.2
		portParaTable OBJECT-TYPE
			SYNTAX SEQUENCE OF PortParaEntry
			MAX-ACCESS not-accessible
			STATUS current
			DESCRIPTION
				" "
			::= { portPara 2 }


--          1.3.6.1.4.1.33922.106.4.2.1
-- 1.3.6.1.4.1.33922.106.4.2.1
-- 1.3.6.1.4.1.33922.106.4.2.1
-- 1.3.6.1.4.1.33922.106.4.2.1
-- 1.3.6.1.4.1.33922.106.4.2.1
-- 1.3.6.1.4.1.33922.106.4.2.1
-- 1.3.6.1.4.1.33922.106.4.2.1
-- 1.3.6.1.4.1.33922.106.4.2.1
-- 1.3.6.1.4.1.33922.106.4.2.1
		-- 1.3.6.1.4.1.33922.106.4.2.1
		portParaEntry OBJECT-TYPE
			SYNTAX PortParaEntry
			MAX-ACCESS not-accessible
			STATUS current
			DESCRIPTION
				" "
			INDEX { portIndex }
			::= { portParaTable 1 }


		PortParaEntry ::=
			SEQUENCE {
				portIndex
					Integer32,
				portName
					DisplayString,
				portEnableID
					INTEGER,
				portID
					Integer32,
				portSpeedSet
					INTEGER,
				portSpeed
					INTEGER,
				portLinkStatus
					INTEGER,
				portUnidirectionalXmitEnable
					INTEGER,
				portTxPower
					DisplayString,
				portRxPower
					DisplayString,
				portVlanPop
					INTEGER,
				portLoopbackEnable
					INTEGER,
				portFEC
					INTEGER,
				portPreambleLeng
					INTEGER,
				portTemperature
					DisplayString,
				portVoltage
					DisplayString,
				portTxBias
					DisplayString,
				portParaRealign
					INTEGER,
				portParaSourceMac
					DisplayString,
				portCascadEnable
					INTEGER,
				portModuleStatus
					INTEGER
			 }

--          1.3.6.1.4.1.33922.106.4.2.1.1
-- 1.3.6.1.4.1.33922.106.4.2.1.1
-- 1.3.6.1.4.1.33922.106.4.2.1.1
-- 1.3.6.1.4.1.33922.106.4.2.1.1
-- 1.3.6.1.4.1.33922.106.4.2.1.1
-- 1.3.6.1.4.1.33922.106.4.2.1.1
-- 1.3.6.1.4.1.33922.106.4.2.1.1
-- 1.3.6.1.4.1.33922.106.4.2.1.1
-- 1.3.6.1.4.1.33922.106.4.2.1.1
		-- 1.3.6.1.4.1.33922.106.4.2.1.1
		portIndex OBJECT-TYPE
			SYNTAX Integer32 (0..100)
			MAX-ACCESS read-only
			STATUS current
			DESCRIPTION
				" "
			::= { portParaEntry 1 }


--          1.3.6.1.4.1.33922.106.4.2.1.2
-- 1.3.6.1.4.1.33922.106.4.2.1.2
-- 1.3.6.1.4.1.33922.106.4.2.1.2
-- 1.3.6.1.4.1.33922.106.4.2.1.2
-- 1.3.6.1.4.1.33922.106.4.2.1.2
-- 1.3.6.1.4.1.33922.106.4.2.1.2
-- 1.3.6.1.4.1.33922.106.4.2.1.2
-- 1.3.6.1.4.1.33922.106.4.2.1.2
-- 1.3.6.1.4.1.33922.106.4.2.1.2
		-- 1.3.6.1.4.1.33922.106.4.2.1.2
		portName OBJECT-TYPE
			SYNTAX DisplayString (SIZE (0..29))
			MAX-ACCESS read-only
			STATUS current
			DESCRIPTION
				"port name.
				to identify the port"
			::= { portParaEntry 2 }


--          1.3.6.1.4.1.33922.106.4.2.1.3
-- 1.3.6.1.4.1.33922.106.4.2.1.3
-- 1.3.6.1.4.1.33922.106.4.2.1.3
-- 1.3.6.1.4.1.33922.106.4.2.1.3
-- 1.3.6.1.4.1.33922.106.4.2.1.3
-- 1.3.6.1.4.1.33922.106.4.2.1.3
-- 1.3.6.1.4.1.33922.106.4.2.1.3
-- 1.3.6.1.4.1.33922.106.4.2.1.3
-- 1.3.6.1.4.1.33922.106.4.2.1.3
		-- 1.3.6.1.4.1.33922.106.4.2.1.3
		portEnableID OBJECT-TYPE
			SYNTAX INTEGER
				{
				disable(0),
				enable(1)
				}
			MAX-ACCESS read-only
			STATUS current
			DESCRIPTION
				"enable port VLAN"
			::= { portParaEntry 3 }


--          1.3.6.1.4.1.33922.106.4.2.1.4
-- 1.3.6.1.4.1.33922.106.4.2.1.4
-- 1.3.6.1.4.1.33922.106.4.2.1.4
-- 1.3.6.1.4.1.33922.106.4.2.1.4
-- 1.3.6.1.4.1.33922.106.4.2.1.4
-- 1.3.6.1.4.1.33922.106.4.2.1.4
-- 1.3.6.1.4.1.33922.106.4.2.1.4
-- 1.3.6.1.4.1.33922.106.4.2.1.4
-- 1.3.6.1.4.1.33922.106.4.2.1.4
		-- 1.3.6.1.4.1.33922.106.4.2.1.4
		portID OBJECT-TYPE
			SYNTAX Integer32 (2..4095)
			MAX-ACCESS read-only
			STATUS current
			DESCRIPTION
				"port vlan id.
				vlanID = firstVlanld + port index
				to identify the data from this port"
			::= { portParaEntry 4 }


--          1.3.6.1.4.1.33922.106.4.2.1.5
-- 1.3.6.1.4.1.33922.106.4.2.1.5
-- 1.3.6.1.4.1.33922.106.4.2.1.5
-- 1.3.6.1.4.1.33922.106.4.2.1.5
-- 1.3.6.1.4.1.33922.106.4.2.1.5
-- 1.3.6.1.4.1.33922.106.4.2.1.5
-- 1.3.6.1.4.1.33922.106.4.2.1.5
-- 1.3.6.1.4.1.33922.106.4.2.1.5
-- 1.3.6.1.4.1.33922.106.4.2.1.5
		-- 1.3.6.1.4.1.33922.106.4.2.1.5
		portSpeedSet OBJECT-TYPE
			SYNTAX INTEGER
				{
				auto(0),
				port1G(1),
				port10G(2),
				port40G(3),
				port100G(4),
				port200G(5),
				port25G(6)
				}
			MAX-ACCESS read-only
			STATUS current
			DESCRIPTION
				"port  speed:
				"
			::= { portParaEntry 5 }


--          1.3.6.1.4.1.33922.106.4.2.1.6
-- 1.3.6.1.4.1.33922.106.4.2.1.6
-- 1.3.6.1.4.1.33922.106.4.2.1.6
-- 1.3.6.1.4.1.33922.106.4.2.1.6
-- 1.3.6.1.4.1.33922.106.4.2.1.6
-- 1.3.6.1.4.1.33922.106.4.2.1.6
-- 1.3.6.1.4.1.33922.106.4.2.1.6
-- 1.3.6.1.4.1.33922.106.4.2.1.6
-- 1.3.6.1.4.1.33922.106.4.2.1.6
		-- 1.3.6.1.4.1.33922.106.4.2.1.6
		portSpeed OBJECT-TYPE
			SYNTAX INTEGER
				{
				auto(0),
				port1G(1),
				port10G(2),
				port40G(3),
				port100G(4),
				port200G(5),
				port25G(6)
				}
			MAX-ACCESS read-only
			STATUS current
			DESCRIPTION
				"Description."
			::= { portParaEntry 6 }


--          1.3.6.1.4.1.33922.106.4.2.1.7
-- 1.3.6.1.4.1.33922.106.4.2.1.7
-- 1.3.6.1.4.1.33922.106.4.2.1.7
-- 1.3.6.1.4.1.33922.106.4.2.1.7
-- 1.3.6.1.4.1.33922.106.4.2.1.7
-- 1.3.6.1.4.1.33922.106.4.2.1.7
-- 1.3.6.1.4.1.33922.106.4.2.1.7
-- 1.3.6.1.4.1.33922.106.4.2.1.7
-- 1.3.6.1.4.1.33922.106.4.2.1.7
		-- 1.3.6.1.4.1.33922.106.4.2.1.7
		portLinkStatus OBJECT-TYPE
			SYNTAX INTEGER
				{
				down(0),
				up(1)
				}
			MAX-ACCESS read-only
			STATUS current
			DESCRIPTION
				"port link status"
			::= { portParaEntry 7 }


--          1.3.6.1.4.1.33922.106.4.2.1.8
-- 1.3.6.1.4.1.33922.106.4.2.1.8
-- 1.3.6.1.4.1.33922.106.4.2.1.8
-- 1.3.6.1.4.1.33922.106.4.2.1.8
-- 1.3.6.1.4.1.33922.106.4.2.1.8
-- 1.3.6.1.4.1.33922.106.4.2.1.8
-- 1.3.6.1.4.1.33922.106.4.2.1.8
-- 1.3.6.1.4.1.33922.106.4.2.1.8
-- 1.3.6.1.4.1.33922.106.4.2.1.8
		-- 1.3.6.1.4.1.33922.106.4.2.1.8
		portUnidirectionalXmitEnable OBJECT-TYPE
			SYNTAX INTEGER
				{
				disable(0),
				enable(1)
				}
			MAX-ACCESS read-only
			STATUS current
			DESCRIPTION
				"port one-way transmission enable switch
				"
			::= { portParaEntry 8 }


--          1.3.6.1.4.1.33922.106.4.2.1.9
-- 1.3.6.1.4.1.33922.106.4.2.1.9
-- 1.3.6.1.4.1.33922.106.4.2.1.9
-- 1.3.6.1.4.1.33922.106.4.2.1.9
-- 1.3.6.1.4.1.33922.106.4.2.1.9
-- 1.3.6.1.4.1.33922.106.4.2.1.9
-- 1.3.6.1.4.1.33922.106.4.2.1.9
-- 1.3.6.1.4.1.33922.106.4.2.1.9
-- 1.3.6.1.4.1.33922.106.4.2.1.9
		-- 1.3.6.1.4.1.33922.106.4.2.1.9
		portTxPower OBJECT-TYPE
			SYNTAX DisplayString
			UNITS "dbm"
			MAX-ACCESS read-only
			STATUS current
			DESCRIPTION
				"Description."
			::= { portParaEntry 9 }


--          1.3.6.1.4.1.33922.106.4.2.1.10
-- 1.3.6.1.4.1.33922.106.4.2.1.10
-- 1.3.6.1.4.1.33922.106.4.2.1.10
-- 1.3.6.1.4.1.33922.106.4.2.1.10
-- 1.3.6.1.4.1.33922.106.4.2.1.10
-- 1.3.6.1.4.1.33922.106.4.2.1.10
-- 1.3.6.1.4.1.33922.106.4.2.1.10
-- 1.3.6.1.4.1.33922.106.4.2.1.10
-- 1.3.6.1.4.1.33922.106.4.2.1.10
		-- 1.3.6.1.4.1.33922.106.4.2.1.10
		portRxPower OBJECT-TYPE
			SYNTAX DisplayString
			UNITS "dbm"
			MAX-ACCESS read-only
			STATUS current
			DESCRIPTION
				"Description."
			::= { portParaEntry 10 }


--          1.3.6.1.4.1.33922.106.4.2.1.11
-- 1.3.6.1.4.1.33922.106.4.2.1.11
-- 1.3.6.1.4.1.33922.106.4.2.1.11
-- 1.3.6.1.4.1.33922.106.4.2.1.11
-- 1.3.6.1.4.1.33922.106.4.2.1.11
-- 1.3.6.1.4.1.33922.106.4.2.1.11
-- 1.3.6.1.4.1.33922.106.4.2.1.11
-- 1.3.6.1.4.1.33922.106.4.2.1.11
-- 1.3.6.1.4.1.33922.106.4.2.1.11
		-- 1.3.6.1.4.1.33922.106.4.2.1.11
		portVlanPop OBJECT-TYPE
			SYNTAX INTEGER
				{
				disable(0),
				outer1(1),
				outer2(2)
				}
			MAX-ACCESS read-only
			STATUS current
			DESCRIPTION
				"Description."
			::= { portParaEntry 11 }


--          1.3.6.1.4.1.33922.106.4.2.1.12
-- 1.3.6.1.4.1.33922.106.4.2.1.12
-- 1.3.6.1.4.1.33922.106.4.2.1.12
-- 1.3.6.1.4.1.33922.106.4.2.1.12
-- 1.3.6.1.4.1.33922.106.4.2.1.12
-- 1.3.6.1.4.1.33922.106.4.2.1.12
-- 1.3.6.1.4.1.33922.106.4.2.1.12
-- 1.3.6.1.4.1.33922.106.4.2.1.12
-- 1.3.6.1.4.1.33922.106.4.2.1.12
		-- 1.3.6.1.4.1.33922.106.4.2.1.12
		portLoopbackEnable OBJECT-TYPE
			SYNTAX INTEGER
				{
				disable(1),
				localLB(2),
				remoterLB(3)
				}
			MAX-ACCESS read-only
			STATUS current
			DESCRIPTION
				"Description."
			::= { portParaEntry 12 }


--          1.3.6.1.4.1.33922.106.4.2.1.13
-- 1.3.6.1.4.1.33922.106.4.2.1.13
-- 1.3.6.1.4.1.33922.106.4.2.1.13
-- 1.3.6.1.4.1.33922.106.4.2.1.13
-- 1.3.6.1.4.1.33922.106.4.2.1.13
-- 1.3.6.1.4.1.33922.106.4.2.1.13
-- 1.3.6.1.4.1.33922.106.4.2.1.13
-- 1.3.6.1.4.1.33922.106.4.2.1.13
-- 1.3.6.1.4.1.33922.106.4.2.1.13
		-- 1.3.6.1.4.1.33922.106.4.2.1.13
		portFEC OBJECT-TYPE
			SYNTAX INTEGER
				{
				not-support(-1),
				disable(0),
				enable(1)
				}
			MAX-ACCESS read-only
			STATUS current
			DESCRIPTION
				"Description."
			::= { portParaEntry 13 }


--          1.3.6.1.4.1.33922.106.4.2.1.14
-- 1.3.6.1.4.1.33922.106.4.2.1.14
-- 1.3.6.1.4.1.33922.106.4.2.1.14
-- 1.3.6.1.4.1.33922.106.4.2.1.14
-- 1.3.6.1.4.1.33922.106.4.2.1.14
-- 1.3.6.1.4.1.33922.106.4.2.1.14
-- 1.3.6.1.4.1.33922.106.4.2.1.14
-- 1.3.6.1.4.1.33922.106.4.2.1.14
-- 1.3.6.1.4.1.33922.106.4.2.1.14
		-- 1.3.6.1.4.1.33922.106.4.2.1.14
		portPreambleLeng OBJECT-TYPE
			SYNTAX INTEGER
				{
				b4(4),
				b8(8)
				}
			MAX-ACCESS read-only
			STATUS current
			DESCRIPTION
				"Description."
			::= { portParaEntry 14 }


--          1.3.6.1.4.1.33922.106.4.2.1.15
-- 1.3.6.1.4.1.33922.106.4.2.1.15
-- 1.3.6.1.4.1.33922.106.4.2.1.15
-- 1.3.6.1.4.1.33922.106.4.2.1.15
-- 1.3.6.1.4.1.33922.106.4.2.1.15
-- 1.3.6.1.4.1.33922.106.4.2.1.15
-- 1.3.6.1.4.1.33922.106.4.2.1.15
-- 1.3.6.1.4.1.33922.106.4.2.1.15
-- 1.3.6.1.4.1.33922.106.4.2.1.15
		-- 1.3.6.1.4.1.33922.106.4.2.1.15
		portTemperature OBJECT-TYPE
			SYNTAX DisplayString
			MAX-ACCESS read-only
			STATUS current
			DESCRIPTION
				"Description."
			::= { portParaEntry 15 }


--          1.3.6.1.4.1.33922.106.4.2.1.16
-- 1.3.6.1.4.1.33922.106.4.2.1.16
-- 1.3.6.1.4.1.33922.106.4.2.1.16
-- 1.3.6.1.4.1.33922.106.4.2.1.16
-- 1.3.6.1.4.1.33922.106.4.2.1.16
-- 1.3.6.1.4.1.33922.106.4.2.1.16
-- 1.3.6.1.4.1.33922.106.4.2.1.16
-- 1.3.6.1.4.1.33922.106.4.2.1.16
-- 1.3.6.1.4.1.33922.106.4.2.1.16
		-- 1.3.6.1.4.1.33922.106.4.2.1.16
		portVoltage OBJECT-TYPE
			SYNTAX DisplayString
			MAX-ACCESS read-only
			STATUS current
			DESCRIPTION
				"Description."
			::= { portParaEntry 16 }


--          1.3.6.1.4.1.33922.106.4.2.1.17
-- 1.3.6.1.4.1.33922.106.4.2.1.17
-- 1.3.6.1.4.1.33922.106.4.2.1.17
-- 1.3.6.1.4.1.33922.106.4.2.1.17
-- 1.3.6.1.4.1.33922.106.4.2.1.17
-- 1.3.6.1.4.1.33922.106.4.2.1.17
-- 1.3.6.1.4.1.33922.106.4.2.1.17
-- 1.3.6.1.4.1.33922.106.4.2.1.17
-- 1.3.6.1.4.1.33922.106.4.2.1.17
		-- 1.3.6.1.4.1.33922.106.4.2.1.17
		portTxBias OBJECT-TYPE
			SYNTAX DisplayString
			MAX-ACCESS read-only
			STATUS current
			DESCRIPTION
				"Description."
			::= { portParaEntry 17 }


--          1.3.6.1.4.1.33922.106.4.2.1.18
-- 1.3.6.1.4.1.33922.106.4.2.1.18
-- 1.3.6.1.4.1.33922.106.4.2.1.18
-- 1.3.6.1.4.1.33922.106.4.2.1.18
-- 1.3.6.1.4.1.33922.106.4.2.1.18
-- 1.3.6.1.4.1.33922.106.4.2.1.18
-- 1.3.6.1.4.1.33922.106.4.2.1.18
-- 1.3.6.1.4.1.33922.106.4.2.1.18
-- 1.3.6.1.4.1.33922.106.4.2.1.18
		-- 1.3.6.1.4.1.33922.106.4.2.1.18
		portParaRealign OBJECT-TYPE
			SYNTAX INTEGER
				{
				split(0),
				merge(1)
				}
			MAX-ACCESS read-only
			STATUS current
			DESCRIPTION
				"only for 40G or 100G PORT"
			::= { portParaEntry 18 }


--       1.3.6.1.4.1.33922.106.4.2.1.19
-- 1.3.6.1.4.1.33922.106.4.2.1.19
-- 1.3.6.1.4.1.33922.106.4.2.1.19
-- 1.3.6.1.4.1.33922.106.4.2.1.19
-- 1.3.6.1.4.1.33922.106.4.2.1.19
-- 1.3.6.1.4.1.33922.106.4.2.1.19
		-- 1.3.6.1.4.1.33922.106.4.2.1.19
		portParaSourceMac OBJECT-TYPE
			SYNTAX DisplayString
			MAX-ACCESS read-only
			STATUS current
			DESCRIPTION
				"Description."
			::= { portParaEntry 19 }


--       1.3.6.1.4.1.33922.106.4.2.1.20
-- 1.3.6.1.4.1.33922.106.4.2.1.20
-- 1.3.6.1.4.1.33922.106.4.2.1.20
-- 1.3.6.1.4.1.33922.106.4.2.1.20
-- 1.3.6.1.4.1.33922.106.4.2.1.20
-- 1.3.6.1.4.1.33922.106.4.2.1.20
		-- 1.3.6.1.4.1.33922.106.4.2.1.20
		portCascadEnable OBJECT-TYPE
			SYNTAX INTEGER
				{
				disable(0),
				enable(1)
				}
			MAX-ACCESS read-only
			STATUS current
			DESCRIPTION
				"Description."
			::= { portParaEntry 20 }


--      1.3.6.1.4.1.33922.106.4.2.1.21
-- 1.3.6.1.4.1.33922.106.4.2.1.21
-- 1.3.6.1.4.1.33922.106.4.2.1.21
-- 1.3.6.1.4.1.33922.106.4.2.1.21
-- 1.3.6.1.4.1.33922.106.4.2.1.21
		-- 1.3.6.1.4.1.33922.106.4.2.1.21
		portModuleStatus OBJECT-TYPE
			SYNTAX INTEGER
				{
				abs(0),
				present(1)
				}
			MAX-ACCESS read-only
			STATUS current
			DESCRIPTION
				"Description."
			::= { portParaEntry 21 }


--          1.3.6.1.4.1.33922.106.7
-- 1.3.6.1.4.1.33922.106.7
-- 1.3.6.1.4.1.33922.106.7
-- 1.3.6.1.4.1.33922.106.7
-- 1.3.6.1.4.1.33922.106.5
-- 1.3.6.1.4.1.33922.106.5
-- 1.3.6.1.4.1.33922.106.5
-- 1.3.6.1.4.1.33922.106.5
-- 1.3.6.1.4.1.33922.106.5
		-- 1.3.6.1.4.1.33922.106.5
		portStatistics OBJECT IDENTIFIER ::= { BYZORO-T7600 5 }


--          1.3.6.1.4.1.33922.106.7.1
-- 1.3.6.1.4.1.33922.106.7.1
-- 1.3.6.1.4.1.33922.106.7.1
-- 1.3.6.1.4.1.33922.106.7.1
-- 1.3.6.1.4.1.33922.106.5.1
-- 1.3.6.1.4.1.33922.106.5.1
-- 1.3.6.1.4.1.33922.106.5.1
-- 1.3.6.1.4.1.33922.106.5.1
-- 1.3.6.1.4.1.33922.106.5.1
		-- 1.3.6.1.4.1.33922.106.5.1
		sendDrop OBJECT-TYPE
			SYNTAX Counter64
			MAX-ACCESS read-only
			STATUS current
			DESCRIPTION
				"Description."
			::= { portStatistics 1 }


--          1.3.6.1.4.1.33922.106.7.2
-- 1.3.6.1.4.1.33922.106.7.2
-- 1.3.6.1.4.1.33922.106.7.2
-- 1.3.6.1.4.1.33922.106.7.2
-- 1.3.6.1.4.1.33922.106.5.2
-- 1.3.6.1.4.1.33922.106.5.2
-- 1.3.6.1.4.1.33922.106.5.2
-- 1.3.6.1.4.1.33922.106.5.2
-- 1.3.6.1.4.1.33922.106.5.2
		-- 1.3.6.1.4.1.33922.106.5.2
		portStatisticsTable OBJECT-TYPE
			SYNTAX SEQUENCE OF PortStatisticsEntry
			MAX-ACCESS not-accessible
			STATUS current
			DESCRIPTION
				" "
			::= { portStatistics 2 }


--          1.3.6.1.4.1.33922.106.7.2.1
-- 1.3.6.1.4.1.33922.106.7.2.1
-- 1.3.6.1.4.1.33922.106.7.2.1
-- 1.3.6.1.4.1.33922.106.7.2.1
-- 1.3.6.1.4.1.33922.106.5.2.1
-- 1.3.6.1.4.1.33922.106.5.2.1
-- 1.3.6.1.4.1.33922.106.5.2.1
-- 1.3.6.1.4.1.33922.106.5.2.1
-- 1.3.6.1.4.1.33922.106.5.2.1
		-- 1.3.6.1.4.1.33922.106.5.2.1
		portStatisticsEntry OBJECT-TYPE
			SYNTAX PortStatisticsEntry
			MAX-ACCESS not-accessible
			STATUS current
			DESCRIPTION
				" "
			INDEX { portIndex }
			::= { portStatisticsTable 1 }


		PortStatisticsEntry ::=
			SEQUENCE {
				recvGoodPackets
					Counter64,
				sendGoodPackets
					Counter64,
				recvThroughput
					DisplayString,
				sendThroughput
					DisplayString,
				recvUtilization
					DisplayString,
				sendUtilization
					DisplayString,
				recvBadBytes
					Counter64,
				sendBadBytes
					Counter64,
				sendBadPackets
					Counter64,
				recvGoodBytes
					Counter64,
				sendGoodBytes
					Counter64,
				recvCrcErrors
					Counter64,
				recvOverflowDrops
					Counter64
			 }

--          1.3.6.1.4.1.33922.106.7.2.1.1
-- 1.3.6.1.4.1.33922.106.7.2.1.1
-- 1.3.6.1.4.1.33922.106.7.2.1.1
-- 1.3.6.1.4.1.33922.106.7.2.1.1
-- 1.3.6.1.4.1.33922.106.5.2.1.1
-- 1.3.6.1.4.1.33922.106.5.2.1.1
-- 1.3.6.1.4.1.33922.106.5.2.1.1
-- 1.3.6.1.4.1.33922.106.5.2.1.1
-- 1.3.6.1.4.1.33922.106.5.2.1.1
		-- 1.3.6.1.4.1.33922.106.5.2.1.1
		recvGoodPackets OBJECT-TYPE
			SYNTAX Counter64
			MAX-ACCESS read-only
			STATUS current
			DESCRIPTION
				"the number of good packets "
			::= { portStatisticsEntry 1 }


--          1.3.6.1.4.1.33922.106.7.2.1.2
-- 1.3.6.1.4.1.33922.106.7.2.1.2
-- 1.3.6.1.4.1.33922.106.7.2.1.2
-- 1.3.6.1.4.1.33922.106.7.2.1.2
-- 1.3.6.1.4.1.33922.106.5.2.1.2
-- 1.3.6.1.4.1.33922.106.5.2.1.2
-- 1.3.6.1.4.1.33922.106.5.2.1.2
-- 1.3.6.1.4.1.33922.106.5.2.1.2
-- 1.3.6.1.4.1.33922.106.5.2.1.2
		-- 1.3.6.1.4.1.33922.106.5.2.1.2
		sendGoodPackets OBJECT-TYPE
			SYNTAX Counter64
			MAX-ACCESS read-only
			STATUS current
			DESCRIPTION
				"the number of good packets"
			::= { portStatisticsEntry 2 }


--          1.3.6.1.4.1.33922.106.7.2.1.3
-- 1.3.6.1.4.1.33922.106.7.2.1.3
-- 1.3.6.1.4.1.33922.106.7.2.1.3
-- 1.3.6.1.4.1.33922.106.7.2.1.3
-- 1.3.6.1.4.1.33922.106.5.2.1.3
-- 1.3.6.1.4.1.33922.106.5.2.1.3
-- 1.3.6.1.4.1.33922.106.5.2.1.3
-- 1.3.6.1.4.1.33922.106.5.2.1.3
-- 1.3.6.1.4.1.33922.106.5.2.1.3
		-- 1.3.6.1.4.1.33922.106.5.2.1.3
		recvThroughput OBJECT-TYPE
			SYNTAX DisplayString
			MAX-ACCESS read-only
			STATUS current
			DESCRIPTION
				"the net port throughput (Mbps)"
			::= { portStatisticsEntry 3 }


--          1.3.6.1.4.1.33922.106.7.2.1.4
-- 1.3.6.1.4.1.33922.106.7.2.1.4
-- 1.3.6.1.4.1.33922.106.7.2.1.4
-- 1.3.6.1.4.1.33922.106.7.2.1.4
-- 1.3.6.1.4.1.33922.106.5.2.1.4
-- 1.3.6.1.4.1.33922.106.5.2.1.4
-- 1.3.6.1.4.1.33922.106.5.2.1.4
-- 1.3.6.1.4.1.33922.106.5.2.1.4
-- 1.3.6.1.4.1.33922.106.5.2.1.4
		-- 1.3.6.1.4.1.33922.106.5.2.1.4
		sendThroughput OBJECT-TYPE
			SYNTAX DisplayString
			MAX-ACCESS read-only
			STATUS current
			DESCRIPTION
				"the monitor port throughput (Mbps)"
			::= { portStatisticsEntry 4 }


--          1.3.6.1.4.1.33922.106.7.2.1.5
-- 1.3.6.1.4.1.33922.106.7.2.1.5
-- 1.3.6.1.4.1.33922.106.7.2.1.5
-- 1.3.6.1.4.1.33922.106.7.2.1.5
-- 1.3.6.1.4.1.33922.106.5.2.1.5
-- 1.3.6.1.4.1.33922.106.5.2.1.5
-- 1.3.6.1.4.1.33922.106.5.2.1.5
-- 1.3.6.1.4.1.33922.106.5.2.1.5
-- 1.3.6.1.4.1.33922.106.5.2.1.5
		-- 1.3.6.1.4.1.33922.106.5.2.1.5
		recvUtilization OBJECT-TYPE
			SYNTAX DisplayString
			MAX-ACCESS read-only
			STATUS current
			DESCRIPTION
				"the net port utilization(%)"
			::= { portStatisticsEntry 5 }


--          1.3.6.1.4.1.33922.106.7.2.1.6
-- 1.3.6.1.4.1.33922.106.7.2.1.6
-- 1.3.6.1.4.1.33922.106.7.2.1.6
-- 1.3.6.1.4.1.33922.106.7.2.1.6
-- 1.3.6.1.4.1.33922.106.5.2.1.6
-- 1.3.6.1.4.1.33922.106.5.2.1.6
-- 1.3.6.1.4.1.33922.106.5.2.1.6
-- 1.3.6.1.4.1.33922.106.5.2.1.6
-- 1.3.6.1.4.1.33922.106.5.2.1.6
		-- 1.3.6.1.4.1.33922.106.5.2.1.6
		sendUtilization OBJECT-TYPE
			SYNTAX DisplayString
			MAX-ACCESS read-only
			STATUS current
			DESCRIPTION
				"the monitor port utilization(%)"
			::= { portStatisticsEntry 6 }


--          1.3.6.1.4.1.33922.106.7.2.1.7
-- 1.3.6.1.4.1.33922.106.7.2.1.7
-- 1.3.6.1.4.1.33922.106.7.2.1.7
-- 1.3.6.1.4.1.33922.106.7.2.1.7
-- 1.3.6.1.4.1.33922.106.5.2.1.7
-- 1.3.6.1.4.1.33922.106.5.2.1.7
-- 1.3.6.1.4.1.33922.106.5.2.1.7
-- 1.3.6.1.4.1.33922.106.5.2.1.7
-- 1.3.6.1.4.1.33922.106.5.2.1.7
		-- 1.3.6.1.4.1.33922.106.5.2.1.7
		recvBadBytes OBJECT-TYPE
			SYNTAX Counter64
			MAX-ACCESS read-only
			STATUS current
			DESCRIPTION
				"Description."
			::= { portStatisticsEntry 7 }


--          1.3.6.1.4.1.33922.106.7.2.1.8
-- 1.3.6.1.4.1.33922.106.7.2.1.8
-- 1.3.6.1.4.1.33922.106.7.2.1.8
-- 1.3.6.1.4.1.33922.106.7.2.1.8
-- 1.3.6.1.4.1.33922.106.5.2.1.8
-- 1.3.6.1.4.1.33922.106.5.2.1.8
-- 1.3.6.1.4.1.33922.106.5.2.1.8
-- 1.3.6.1.4.1.33922.106.5.2.1.8
-- 1.3.6.1.4.1.33922.106.5.2.1.8
		-- 1.3.6.1.4.1.33922.106.5.2.1.8
		sendBadBytes OBJECT-TYPE
			SYNTAX Counter64
			MAX-ACCESS read-only
			STATUS current
			DESCRIPTION
				"Description."
			::= { portStatisticsEntry 8 }


--          1.3.6.1.4.1.33922.106.7.2.1.9
-- 1.3.6.1.4.1.33922.106.7.2.1.9
-- 1.3.6.1.4.1.33922.106.7.2.1.9
-- 1.3.6.1.4.1.33922.106.7.2.1.9
-- 1.3.6.1.4.1.33922.106.5.2.1.9
-- 1.3.6.1.4.1.33922.106.5.2.1.9
-- 1.3.6.1.4.1.33922.106.5.2.1.9
-- 1.3.6.1.4.1.33922.106.5.2.1.9
-- 1.3.6.1.4.1.33922.106.5.2.1.9
		-- 1.3.6.1.4.1.33922.106.5.2.1.9
		sendBadPackets OBJECT-TYPE
			SYNTAX Counter64
			MAX-ACCESS read-only
			STATUS current
			DESCRIPTION
				"Description."
			::= { portStatisticsEntry 9 }


--          1.3.6.1.4.1.33922.106.7.2.1.10
-- 1.3.6.1.4.1.33922.106.7.2.1.10
-- 1.3.6.1.4.1.33922.106.7.2.1.10
-- 1.3.6.1.4.1.33922.106.7.2.1.10
-- 1.3.6.1.4.1.33922.106.5.2.1.10
-- 1.3.6.1.4.1.33922.106.5.2.1.10
-- 1.3.6.1.4.1.33922.106.5.2.1.10
-- 1.3.6.1.4.1.33922.106.5.2.1.10
-- 1.3.6.1.4.1.33922.106.5.2.1.10
		-- 1.3.6.1.4.1.33922.106.5.2.1.10
		recvGoodBytes OBJECT-TYPE
			SYNTAX Counter64
			MAX-ACCESS read-only
			STATUS current
			DESCRIPTION
				"Description."
			::= { portStatisticsEntry 10 }


--          1.3.6.1.4.1.33922.106.7.2.1.11
-- 1.3.6.1.4.1.33922.106.7.2.1.11
-- 1.3.6.1.4.1.33922.106.7.2.1.11
-- 1.3.6.1.4.1.33922.106.7.2.1.11
-- 1.3.6.1.4.1.33922.106.5.2.1.11
-- 1.3.6.1.4.1.33922.106.5.2.1.11
-- 1.3.6.1.4.1.33922.106.5.2.1.11
-- 1.3.6.1.4.1.33922.106.5.2.1.11
-- 1.3.6.1.4.1.33922.106.5.2.1.11
		-- 1.3.6.1.4.1.33922.106.5.2.1.11
		sendGoodBytes OBJECT-TYPE
			SYNTAX Counter64
			MAX-ACCESS read-only
			STATUS current
			DESCRIPTION
				"Description."
			::= { portStatisticsEntry 11 }


--          1.3.6.1.4.1.33922.106.7.2.1.12
-- 1.3.6.1.4.1.33922.106.7.2.1.12
-- 1.3.6.1.4.1.33922.106.7.2.1.12
-- 1.3.6.1.4.1.33922.106.7.2.1.12
-- 1.3.6.1.4.1.33922.106.5.2.1.12
-- 1.3.6.1.4.1.33922.106.5.2.1.12
-- 1.3.6.1.4.1.33922.106.5.2.1.12
-- 1.3.6.1.4.1.33922.106.5.2.1.12
-- 1.3.6.1.4.1.33922.106.5.2.1.12
		-- 1.3.6.1.4.1.33922.106.5.2.1.12
		recvCrcErrors OBJECT-TYPE
			SYNTAX Counter64
			MAX-ACCESS read-only
			STATUS current
			DESCRIPTION
				"the number of crc error packets"
			::= { portStatisticsEntry 12 }


--          1.3.6.1.4.1.33922.106.7.2.1.13
-- 1.3.6.1.4.1.33922.106.7.2.1.13
-- 1.3.6.1.4.1.33922.106.7.2.1.13
-- 1.3.6.1.4.1.33922.106.7.2.1.13
-- 1.3.6.1.4.1.33922.106.5.2.1.13
-- 1.3.6.1.4.1.33922.106.5.2.1.13
-- 1.3.6.1.4.1.33922.106.5.2.1.13
-- 1.3.6.1.4.1.33922.106.5.2.1.13
-- 1.3.6.1.4.1.33922.106.5.2.1.13
		-- 1.3.6.1.4.1.33922.106.5.2.1.13
		recvOverflowDrops OBJECT-TYPE
			SYNTAX Counter64
			MAX-ACCESS read-only
			STATUS current
			DESCRIPTION
				"Description."
			::= { portStatisticsEntry 13 }


--          1.3.6.1.4.1.33922.106.9
-- 1.3.6.1.4.1.33922.106.9
-- 1.3.6.1.4.1.33922.106.9
-- 1.3.6.1.4.1.33922.106.11
-- 1.3.6.1.4.1.33922.106.6
-- 1.3.6.1.4.1.33922.106.6
-- 1.3.6.1.4.1.33922.106.6
-- 1.3.6.1.4.1.33922.106.6
-- 1.3.6.1.4.1.33922.106.6
		-- 1.3.6.1.4.1.33922.106.6
		alarm OBJECT IDENTIFIER ::= { BYZORO-T7600 6 }


--          1.3.6.1.4.1.33922.106.9.1
-- 1.3.6.1.4.1.33922.106.9.1
-- 1.3.6.1.4.1.33922.106.9.1
-- 1.3.6.1.4.1.33922.106.11.1
-- 1.3.6.1.4.1.33922.106.6.1
-- 1.3.6.1.4.1.33922.106.6.1
-- 1.3.6.1.4.1.33922.106.6.1
-- 1.3.6.1.4.1.33922.106.6.1
-- 1.3.6.1.4.1.33922.106.6.1
		-- 1.3.6.1.4.1.33922.106.6.1
		cpuAlarm OBJECT-TYPE
			SYNTAX INTEGER
				{
				normal(0),
				alarm(1)
				}
			MAX-ACCESS read-only
			STATUS current
			DESCRIPTION
				"cpu alarm"
			::= { alarm 1 }


--          1.3.6.1.4.1.33922.106.9.2
-- 1.3.6.1.4.1.33922.106.9.2
-- 1.3.6.1.4.1.33922.106.9.2
-- 1.3.6.1.4.1.33922.106.11.2
-- 1.3.6.1.4.1.33922.106.6.2
-- 1.3.6.1.4.1.33922.106.6.2
-- 1.3.6.1.4.1.33922.106.6.2
-- 1.3.6.1.4.1.33922.106.6.2
-- 1.3.6.1.4.1.33922.106.6.2
		-- 1.3.6.1.4.1.33922.106.6.2
		memoryAlarm OBJECT-TYPE
			SYNTAX INTEGER
				{
				normal(0),
				alarm(1)
				}
			MAX-ACCESS read-only
			STATUS current
			DESCRIPTION
				"memory alarm"
			::= { alarm 2 }


--          1.3.6.1.4.1.33922.106.9.3
-- 1.3.6.1.4.1.33922.106.9.3
-- 1.3.6.1.4.1.33922.106.9.3
-- 1.3.6.1.4.1.33922.106.11.3
-- 1.3.6.1.4.1.33922.106.6.3
-- 1.3.6.1.4.1.33922.106.6.3
-- 1.3.6.1.4.1.33922.106.6.3
-- 1.3.6.1.4.1.33922.106.6.3
-- 1.3.6.1.4.1.33922.106.6.3
		-- 1.3.6.1.4.1.33922.106.6.3
		storageAlarm OBJECT-TYPE
			SYNTAX INTEGER
				{
				normal(0),
				alarm(1)
				}
			MAX-ACCESS read-only
			STATUS current
			DESCRIPTION
				"storage alarm"
			::= { alarm 3 }


--          1.3.6.1.4.1.33922.106.9.4
-- 1.3.6.1.4.1.33922.106.9.4
-- 1.3.6.1.4.1.33922.106.9.4
-- 1.3.6.1.4.1.33922.106.11.4
-- 1.3.6.1.4.1.33922.106.6.4
-- 1.3.6.1.4.1.33922.106.6.4
-- 1.3.6.1.4.1.33922.106.6.4
-- 1.3.6.1.4.1.33922.106.6.4
-- 1.3.6.1.4.1.33922.106.6.4
		-- 1.3.6.1.4.1.33922.106.6.4
		sysAlarm OBJECT-TYPE
			SYNTAX INTEGER
				{
				normal(0),
				alarm(1)
				}
			MAX-ACCESS read-only
			STATUS current
			DESCRIPTION
				"Description."
			::= { alarm 4 }


--          1.3.6.1.4.1.33922.106.9.5
-- 1.3.6.1.4.1.33922.106.9.5
-- 1.3.6.1.4.1.33922.106.9.5
-- 1.3.6.1.4.1.33922.106.11.5
-- 1.3.6.1.4.1.33922.106.6.5
-- 1.3.6.1.4.1.33922.106.6.5
-- 1.3.6.1.4.1.33922.106.6.5
-- 1.3.6.1.4.1.33922.106.6.5
-- 1.3.6.1.4.1.33922.106.6.5
		-- 1.3.6.1.4.1.33922.106.6.5
		sendDropAlarm OBJECT-TYPE
			SYNTAX INTEGER
				{
				normal(0),
				alarm(1)
				}
			MAX-ACCESS read-only
			STATUS current
			DESCRIPTION
				"Description."
			::= { alarm 5 }


--          1.3.6.1.4.1.33922.106.9.6
-- 1.3.6.1.4.1.33922.106.9.6
-- 1.3.6.1.4.1.33922.106.9.6
-- 1.3.6.1.4.1.33922.106.11.6
-- 1.3.6.1.4.1.33922.106.6.6
-- 1.3.6.1.4.1.33922.106.6.6
-- 1.3.6.1.4.1.33922.106.6.6
-- 1.3.6.1.4.1.33922.106.6.6
-- 1.3.6.1.4.1.33922.106.6.6
		-- 1.3.6.1.4.1.33922.106.6.6
		portAlarmTable OBJECT-TYPE
			SYNTAX SEQUENCE OF PortAlarmEntry
			MAX-ACCESS not-accessible
			STATUS current
			DESCRIPTION
				" "
			::= { alarm 6 }


--          1.3.6.1.4.1.33922.106.9.6.1
-- 1.3.6.1.4.1.33922.106.9.6.1
-- 1.3.6.1.4.1.33922.106.9.6.1
-- 1.3.6.1.4.1.33922.106.11.6.1
-- 1.3.6.1.4.1.33922.106.6.6.1
-- 1.3.6.1.4.1.33922.106.6.6.1
-- 1.3.6.1.4.1.33922.106.6.6.1
-- 1.3.6.1.4.1.33922.106.6.6.1
-- 1.3.6.1.4.1.33922.106.6.6.1
		-- 1.3.6.1.4.1.33922.106.6.6.1
		portAlarmEntry OBJECT-TYPE
			SYNTAX PortAlarmEntry
			MAX-ACCESS not-accessible
			STATUS current
			DESCRIPTION
				" "
			INDEX { portIndex }
			::= { portAlarmTable 1 }


		PortAlarmEntry ::=
			SEQUENCE {
				linkdownAlarm
					INTEGER,
				recvErrAlarm
					INTEGER,
				sendErrAlarm
					INTEGER,
				portRecvUtilizationAlarm
					INTEGER,
				portSendUtilizationAlarm
					INTEGER,
				overflowAlarm
					INTEGER,
				opticalPortTempAlarm
					INTEGER,
				opticalPortVccAlarm
					INTEGER,
				opticalPortTxBiasAlarm
					INTEGER,
				opticalPortTxPowerAlarm
					INTEGER,
				opticalPortRxPowerAlarm
					INTEGER
			 }

--          1.3.6.1.4.1.33922.106.9.6.1.1
-- 1.3.6.1.4.1.33922.106.9.6.1.1
-- 1.3.6.1.4.1.33922.106.9.6.1.1
-- 1.3.6.1.4.1.33922.106.11.6.1.1
-- 1.3.6.1.4.1.33922.106.6.6.1.1
-- 1.3.6.1.4.1.33922.106.6.6.1.1
-- 1.3.6.1.4.1.33922.106.6.6.1.1
-- 1.3.6.1.4.1.33922.106.6.6.1.1
-- 1.3.6.1.4.1.33922.106.6.6.1.1
		-- 1.3.6.1.4.1.33922.106.6.6.1.1
		linkdownAlarm OBJECT-TYPE
			SYNTAX INTEGER
				{
				normal(0),
				alarm(1)
				}
			MAX-ACCESS read-only
			STATUS current
			DESCRIPTION
				"Description."
			::= { portAlarmEntry 1 }


--          1.3.6.1.4.1.33922.106.9.6.1.2
-- 1.3.6.1.4.1.33922.106.9.6.1.2
-- 1.3.6.1.4.1.33922.106.9.6.1.2
-- 1.3.6.1.4.1.33922.106.11.6.1.2
-- 1.3.6.1.4.1.33922.106.6.6.1.2
-- 1.3.6.1.4.1.33922.106.6.6.1.2
-- 1.3.6.1.4.1.33922.106.6.6.1.2
-- 1.3.6.1.4.1.33922.106.6.6.1.2
-- 1.3.6.1.4.1.33922.106.6.6.1.2
		-- 1.3.6.1.4.1.33922.106.6.6.1.2
		recvErrAlarm OBJECT-TYPE
			SYNTAX INTEGER
				{
				normal(0),
				alarm(1)
				}
			MAX-ACCESS read-only
			STATUS current
			DESCRIPTION
				"receiving packet error alarm"
			::= { portAlarmEntry 2 }


--          1.3.6.1.4.1.33922.106.9.6.1.3
-- 1.3.6.1.4.1.33922.106.9.6.1.3
-- 1.3.6.1.4.1.33922.106.9.6.1.3
-- 1.3.6.1.4.1.33922.106.11.6.1.3
-- 1.3.6.1.4.1.33922.106.6.6.1.3
-- 1.3.6.1.4.1.33922.106.6.6.1.3
-- 1.3.6.1.4.1.33922.106.6.6.1.3
-- 1.3.6.1.4.1.33922.106.6.6.1.3
-- 1.3.6.1.4.1.33922.106.6.6.1.3
		-- 1.3.6.1.4.1.33922.106.6.6.1.3
		sendErrAlarm OBJECT-TYPE
			SYNTAX INTEGER
				{
				normal(0),
				alarm(1)
				}
			MAX-ACCESS read-only
			STATUS current
			DESCRIPTION
				"Description."
			::= { portAlarmEntry 3 }


--          1.3.6.1.4.1.33922.106.9.6.1.4
-- 1.3.6.1.4.1.33922.106.9.6.1.4
-- 1.3.6.1.4.1.33922.106.9.6.1.4
-- 1.3.6.1.4.1.33922.106.11.6.1.4
-- 1.3.6.1.4.1.33922.106.6.6.1.4
-- 1.3.6.1.4.1.33922.106.6.6.1.4
-- 1.3.6.1.4.1.33922.106.6.6.1.4
-- 1.3.6.1.4.1.33922.106.6.6.1.4
-- 1.3.6.1.4.1.33922.106.6.6.1.4
		-- 1.3.6.1.4.1.33922.106.6.6.1.4
		portRecvUtilizationAlarm OBJECT-TYPE
			SYNTAX INTEGER
				{
				normal(0),
				alarm(1)
				}
			MAX-ACCESS read-only
			STATUS current
			DESCRIPTION
				"linkSyncDown alarm"
			::= { portAlarmEntry 4 }


--          1.3.6.1.4.1.33922.106.9.6.1.5
-- 1.3.6.1.4.1.33922.106.9.6.1.5
-- 1.3.6.1.4.1.33922.106.9.6.1.5
-- 1.3.6.1.4.1.33922.106.11.6.1.5
-- 1.3.6.1.4.1.33922.106.6.6.1.5
-- 1.3.6.1.4.1.33922.106.6.6.1.5
-- 1.3.6.1.4.1.33922.106.6.6.1.5
-- 1.3.6.1.4.1.33922.106.6.6.1.5
-- 1.3.6.1.4.1.33922.106.6.6.1.5
		-- 1.3.6.1.4.1.33922.106.6.6.1.5
		portSendUtilizationAlarm OBJECT-TYPE
			SYNTAX INTEGER
				{
				normal(0),
				alarm(1)
				}
			MAX-ACCESS read-only
			STATUS current
			DESCRIPTION
				"port usage alarm"
			::= { portAlarmEntry 5 }


--          1.3.6.1.4.1.33922.106.9.6.1.7
-- 1.3.6.1.4.1.33922.106.9.6.1.7
-- 1.3.6.1.4.1.33922.106.9.6.1.7
-- 1.3.6.1.4.1.33922.106.11.6.1.6
-- 1.3.6.1.4.1.33922.106.6.6.1.6
-- 1.3.6.1.4.1.33922.106.6.6.1.6
-- 1.3.6.1.4.1.33922.106.6.6.1.6
-- 1.3.6.1.4.1.33922.106.6.6.1.6
-- 1.3.6.1.4.1.33922.106.6.6.1.6
		-- 1.3.6.1.4.1.33922.106.6.6.1.6
		overflowAlarm OBJECT-TYPE
			SYNTAX INTEGER
				{
				normal(0),
				alarm(1)
				}
			MAX-ACCESS read-write
			STATUS current
			DESCRIPTION
				"Description."
			::= { portAlarmEntry 6 }


--          1.3.6.1.4.1.33922.106.9.6.1.8
-- 1.3.6.1.4.1.33922.106.9.6.1.8
-- 1.3.6.1.4.1.33922.106.9.6.1.8
-- 1.3.6.1.4.1.33922.106.11.6.1.7
-- 1.3.6.1.4.1.33922.106.6.6.1.7
-- 1.3.6.1.4.1.33922.106.6.6.1.7
-- 1.3.6.1.4.1.33922.106.6.6.1.7
-- 1.3.6.1.4.1.33922.106.6.6.1.7
-- 1.3.6.1.4.1.33922.106.6.6.1.7
		-- 1.3.6.1.4.1.33922.106.6.6.1.7
		opticalPortTempAlarm OBJECT-TYPE
			SYNTAX INTEGER
				{
				normal(0),
				alarm(1)
				}
			MAX-ACCESS read-write
			STATUS current
			DESCRIPTION
				"Description."
			::= { portAlarmEntry 7 }


--          1.3.6.1.4.1.33922.106.9.6.1.10
-- 1.3.6.1.4.1.33922.106.9.6.1.10
-- 1.3.6.1.4.1.33922.106.9.6.1.10
-- 1.3.6.1.4.1.33922.106.11.6.1.8
-- 1.3.6.1.4.1.33922.106.6.6.1.8
-- 1.3.6.1.4.1.33922.106.6.6.1.8
-- 1.3.6.1.4.1.33922.106.6.6.1.8
-- 1.3.6.1.4.1.33922.106.6.6.1.8
-- 1.3.6.1.4.1.33922.106.6.6.1.8
		-- 1.3.6.1.4.1.33922.106.6.6.1.8
		opticalPortVccAlarm OBJECT-TYPE
			SYNTAX INTEGER
				{
				normal(0),
				alarm(1)
				}
			MAX-ACCESS read-write
			STATUS current
			DESCRIPTION
				"Description."
			::= { portAlarmEntry 8 }


--          1.3.6.1.4.1.33922.106.9.6.1.11
-- 1.3.6.1.4.1.33922.106.9.6.1.11
-- 1.3.6.1.4.1.33922.106.9.6.1.11
-- 1.3.6.1.4.1.33922.106.11.6.1.9
-- 1.3.6.1.4.1.33922.106.6.6.1.9
-- 1.3.6.1.4.1.33922.106.6.6.1.9
-- 1.3.6.1.4.1.33922.106.6.6.1.9
-- 1.3.6.1.4.1.33922.106.6.6.1.9
-- 1.3.6.1.4.1.33922.106.6.6.1.9
		-- 1.3.6.1.4.1.33922.106.6.6.1.9
		opticalPortTxBiasAlarm OBJECT-TYPE
			SYNTAX INTEGER
				{
				normal(0),
				alarm(1)
				}
			MAX-ACCESS read-write
			STATUS current
			DESCRIPTION
				"Description."
			::= { portAlarmEntry 9 }


--          1.3.6.1.4.1.33922.106.9.6.1.12
-- 1.3.6.1.4.1.33922.106.9.6.1.12
-- 1.3.6.1.4.1.33922.106.9.6.1.12
-- 1.3.6.1.4.1.33922.106.11.6.1.10
-- 1.3.6.1.4.1.33922.106.6.6.1.10
-- 1.3.6.1.4.1.33922.106.6.6.1.10
-- 1.3.6.1.4.1.33922.106.6.6.1.10
-- 1.3.6.1.4.1.33922.106.6.6.1.10
-- 1.3.6.1.4.1.33922.106.6.6.1.10
		-- 1.3.6.1.4.1.33922.106.6.6.1.10
		opticalPortTxPowerAlarm OBJECT-TYPE
			SYNTAX INTEGER
				{
				normal(0),
				alarm(1)
				}
			MAX-ACCESS read-write
			STATUS current
			DESCRIPTION
				"Description."
			::= { portAlarmEntry 10 }


--          1.3.6.1.4.1.33922.106.9.6.1.13
-- 1.3.6.1.4.1.33922.106.9.6.1.13
-- 1.3.6.1.4.1.33922.106.9.6.1.13
-- 1.3.6.1.4.1.33922.106.11.6.1.11
-- 1.3.6.1.4.1.33922.106.6.6.1.11
-- 1.3.6.1.4.1.33922.106.6.6.1.11
-- 1.3.6.1.4.1.33922.106.6.6.1.11
-- 1.3.6.1.4.1.33922.106.6.6.1.11
-- 1.3.6.1.4.1.33922.106.6.6.1.11
		-- 1.3.6.1.4.1.33922.106.6.6.1.11
		opticalPortRxPowerAlarm OBJECT-TYPE
			SYNTAX INTEGER
				{
				normal(0),
				alarm(1)
				}
			MAX-ACCESS read-write
			STATUS current
			DESCRIPTION
				"Description."
			::= { portAlarmEntry 11 }


--          1.3.6.1.4.1.33922.106.9.7
-- 1.3.6.1.4.1.33922.106.9.7
-- 1.3.6.1.4.1.33922.106.9.7
-- 1.3.6.1.4.1.33922.106.11.7
-- 1.3.6.1.4.1.33922.106.6.7
-- 1.3.6.1.4.1.33922.106.6.7
-- 1.3.6.1.4.1.33922.106.6.7
-- 1.3.6.1.4.1.33922.106.6.7
-- 1.3.6.1.4.1.33922.106.6.7
		-- 1.3.6.1.4.1.33922.106.6.7
		powerAlarmTable OBJECT-TYPE
			SYNTAX SEQUENCE OF PowerAlarmEntry
			MAX-ACCESS not-accessible
			STATUS current
			DESCRIPTION
				"Description."
			::= { alarm 7 }


--          1.3.6.1.4.1.33922.106.9.7.1
-- 1.3.6.1.4.1.33922.106.9.7.1
-- 1.3.6.1.4.1.33922.106.9.7.1
-- 1.3.6.1.4.1.33922.106.11.7.1
-- 1.3.6.1.4.1.33922.106.6.7.1
-- 1.3.6.1.4.1.33922.106.6.7.1
-- 1.3.6.1.4.1.33922.106.6.7.1
-- 1.3.6.1.4.1.33922.106.6.7.1
-- 1.3.6.1.4.1.33922.106.6.7.1
		-- 1.3.6.1.4.1.33922.106.6.7.1
		powerAlarmEntry OBJECT-TYPE
			SYNTAX PowerAlarmEntry
			MAX-ACCESS not-accessible
			STATUS current
			DESCRIPTION
				"Description."
			INDEX { powerIndex }
			::= { powerAlarmTable 1 }


		PowerAlarmEntry ::=
			SEQUENCE {
				powerAlarm
					INTEGER
			 }

--          1.3.6.1.4.1.33922.106.9.7.1.1
-- 1.3.6.1.4.1.33922.106.9.7.1.1
-- 1.3.6.1.4.1.33922.106.9.7.1.1
-- 1.3.6.1.4.1.33922.106.11.7.1.1
-- 1.3.6.1.4.1.33922.106.6.7.1.1
-- 1.3.6.1.4.1.33922.106.6.7.1.1
-- 1.3.6.1.4.1.33922.106.6.7.1.1
-- 1.3.6.1.4.1.33922.106.6.7.1.1
-- 1.3.6.1.4.1.33922.106.6.7.1.1
		-- 1.3.6.1.4.1.33922.106.6.7.1.1
		powerAlarm OBJECT-TYPE
			SYNTAX INTEGER
				{
				normal(0),
				alarm(1)
				}
			MAX-ACCESS read-only
			STATUS current
			DESCRIPTION
				"Description."
			::= { powerAlarmEntry 1 }


--          1.3.6.1.4.1.33922.106.9.8
-- 1.3.6.1.4.1.33922.106.9.8
-- 1.3.6.1.4.1.33922.106.9.8
-- 1.3.6.1.4.1.33922.106.11.8
-- 1.3.6.1.4.1.33922.106.6.8
-- 1.3.6.1.4.1.33922.106.6.8
-- 1.3.6.1.4.1.33922.106.6.8
-- 1.3.6.1.4.1.33922.106.6.8
-- 1.3.6.1.4.1.33922.106.6.8
		-- 1.3.6.1.4.1.33922.106.6.8
		fanAlarmTable OBJECT-TYPE
			SYNTAX SEQUENCE OF FanAlarmEntry
			MAX-ACCESS not-accessible
			STATUS current
			DESCRIPTION
				"Description."
			::= { alarm 8 }


--          1.3.6.1.4.1.33922.106.9.8.1
-- 1.3.6.1.4.1.33922.106.9.8.1
-- 1.3.6.1.4.1.33922.106.9.8.1
-- 1.3.6.1.4.1.33922.106.11.8.1
-- 1.3.6.1.4.1.33922.106.6.8.1
-- 1.3.6.1.4.1.33922.106.6.8.1
-- 1.3.6.1.4.1.33922.106.6.8.1
-- 1.3.6.1.4.1.33922.106.6.8.1
-- 1.3.6.1.4.1.33922.106.6.8.1
		-- 1.3.6.1.4.1.33922.106.6.8.1
		fanAlarmEntry OBJECT-TYPE
			SYNTAX FanAlarmEntry
			MAX-ACCESS not-accessible
			STATUS current
			DESCRIPTION
				"Description."
			INDEX { fanIndex }
			::= { fanAlarmTable 1 }


		FanAlarmEntry ::=
			SEQUENCE {
				fanAlarm
					INTEGER
			 }

--          1.3.6.1.4.1.33922.106.9.8.1.1
-- 1.3.6.1.4.1.33922.106.9.8.1.1
-- 1.3.6.1.4.1.33922.106.9.8.1.1
-- 1.3.6.1.4.1.33922.106.11.8.1.1
-- 1.3.6.1.4.1.33922.106.6.8.1.1
-- 1.3.6.1.4.1.33922.106.6.8.1.1
-- 1.3.6.1.4.1.33922.106.6.8.1.1
-- 1.3.6.1.4.1.33922.106.6.8.1.1
-- 1.3.6.1.4.1.33922.106.6.8.1.1
		-- 1.3.6.1.4.1.33922.106.6.8.1.1
		fanAlarm OBJECT-TYPE
			SYNTAX INTEGER
				{
				normal(0),
				alarm(1)
				}
			MAX-ACCESS read-write
			STATUS current
			DESCRIPTION
				"Description."
			::= { fanAlarmEntry 1 }


--          1.3.6.1.4.1.33922.106.9.9
-- 1.3.6.1.4.1.33922.106.9.9
-- 1.3.6.1.4.1.33922.106.9.9
-- 1.3.6.1.4.1.33922.106.11.9
-- 1.3.6.1.4.1.33922.106.6.9
-- 1.3.6.1.4.1.33922.106.6.9
-- 1.3.6.1.4.1.33922.106.6.9
-- 1.3.6.1.4.1.33922.106.6.9
-- 1.3.6.1.4.1.33922.106.6.9
		-- 1.3.6.1.4.1.33922.106.6.9
		temperatureALarmTable OBJECT-TYPE
			SYNTAX SEQUENCE OF TemperatureALarmEntry
			MAX-ACCESS not-accessible
			STATUS current
			DESCRIPTION
				"Description."
			::= { alarm 9 }


--          1.3.6.1.4.1.33922.106.9.9.1
-- 1.3.6.1.4.1.33922.106.9.9.1
-- 1.3.6.1.4.1.33922.106.9.9.1
-- 1.3.6.1.4.1.33922.106.11.9.1
-- 1.3.6.1.4.1.33922.106.6.9.1
-- 1.3.6.1.4.1.33922.106.6.9.1
-- 1.3.6.1.4.1.33922.106.6.9.1
-- 1.3.6.1.4.1.33922.106.6.9.1
-- 1.3.6.1.4.1.33922.106.6.9.1
		-- 1.3.6.1.4.1.33922.106.6.9.1
		temperatureALarmEntry OBJECT-TYPE
			SYNTAX TemperatureALarmEntry
			MAX-ACCESS not-accessible
			STATUS current
			DESCRIPTION
				"Description."
			INDEX { temperatureIndex }
			::= { temperatureALarmTable 1 }


		TemperatureALarmEntry ::=
			SEQUENCE {
				temperatureAlarm
					INTEGER
			 }

--          1.3.6.1.4.1.33922.106.9.9.1.1
-- 1.3.6.1.4.1.33922.106.9.9.1.1
-- 1.3.6.1.4.1.33922.106.9.9.1.1
-- 1.3.6.1.4.1.33922.106.11.9.1.1
-- 1.3.6.1.4.1.33922.106.6.9.1.1
-- 1.3.6.1.4.1.33922.106.6.9.1.1
-- 1.3.6.1.4.1.33922.106.6.9.1.1
-- 1.3.6.1.4.1.33922.106.6.9.1.1
-- 1.3.6.1.4.1.33922.106.6.9.1.1
		-- 1.3.6.1.4.1.33922.106.6.9.1.1
		temperatureAlarm OBJECT-TYPE
			SYNTAX INTEGER
				{
				normal(0),
				alarm(1)
				}
			MAX-ACCESS read-write
			STATUS current
			DESCRIPTION
				"Description."
			::= { temperatureALarmEntry 1 }


--          1.3.6.1.4.1.33922.106.10
-- 1.3.6.1.4.1.33922.106.10
-- 1.3.6.1.4.1.33922.106.10
-- 1.3.6.1.4.1.33922.106.12
-- 1.3.6.1.4.1.33922.106.7
-- 1.3.6.1.4.1.33922.106.7
-- 1.3.6.1.4.1.33922.106.7
-- 1.3.6.1.4.1.33922.106.7
-- 1.3.6.1.4.1.33922.106.7
		-- 1.3.6.1.4.1.33922.106.7
		trap OBJECT IDENTIFIER ::= { BYZORO-T7600 7 }


--    1.3.6.1.4.1.33922.106.7.1
-- 1.3.6.1.4.1.33922.106.7.1
-- 1.3.6.1.4.1.33922.106.7.1
		-- 1.3.6.1.4.1.33922.106.7.1
		alarmSeverity OBJECT-TYPE
			SYNTAX Integer32
			MAX-ACCESS read-only
			STATUS current
			DESCRIPTION
				"Description."
			::= { trap 1 }


--    1.3.6.1.4.1.33922.106.7.2
-- 1.3.6.1.4.1.33922.106.7.2
-- 1.3.6.1.4.1.33922.106.7.2
		-- 1.3.6.1.4.1.33922.106.7.2
		alarmSource OBJECT-TYPE
			SYNTAX DisplayString
			MAX-ACCESS read-only
			STATUS current
			DESCRIPTION
				"Description."
			::= { trap 2 }


--    1.3.6.1.4.1.33922.106.7.3
-- 1.3.6.1.4.1.33922.106.7.3
-- 1.3.6.1.4.1.33922.106.7.3
		-- 1.3.6.1.4.1.33922.106.7.3
		alarmCause OBJECT-TYPE
			SYNTAX Integer32
			MAX-ACCESS read-only
			STATUS current
			DESCRIPTION
				"Description."
			::= { trap 3 }


--    1.3.6.1.4.1.33922.106.7.4
-- 1.3.6.1.4.1.33922.106.7.4
-- 1.3.6.1.4.1.33922.106.7.4
		-- 1.3.6.1.4.1.33922.106.7.4
		alarmValue OBJECT-TYPE
			SYNTAX DisplayString
			MAX-ACCESS read-only
			STATUS current
			DESCRIPTION
				"Description."
			::= { trap 4 }


--          1.3.6.1.4.1.33922.106.10.5
-- 1.3.6.1.4.1.33922.106.10.5
-- 1.3.6.1.4.1.33922.106.10.5
-- 1.3.6.1.4.1.33922.106.12.5
-- 1.3.6.1.4.1.33922.106.7.5
-- 1.3.6.1.4.1.33922.106.7.5
-- 1.3.6.1.4.1.33922.106.7.5
-- 1.3.6.1.4.1.33922.106.7.5
-- 1.3.6.1.4.1.33922.106.7.5
		-- 1.3.6.1.4.1.33922.106.7.5
		trapAlarmEvent NOTIFICATION-TYPE
			OBJECTS { alarmValue, alarmCause, alarmSource, alarmSeverity }
			STATUS current
			DESCRIPTION
				" "
			::= { trap 5 }



	END

--
-- BYZORO-T7600.mib
--
