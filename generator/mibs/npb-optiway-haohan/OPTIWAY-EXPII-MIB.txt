OE-MIB DEFINITIONS ::= BEGIN

IMPORTS
    MODULE-IDENTITY, OBJECT-TYPE, Counter32,Gauge32, Counter64,
    Integer32,TimeTicks, NOTIFICATION-TYPE, enterprises             
        FROM SNMPv2-SMI
    TEXTUAL-CONVENTION, DisplayString,PhysAddress
       	FROM SNMPv2-TC
    IANAifType                              
    	FROM IANAifType-MIB;

optiwayExpII MODULE-IDENTITY 
    LAST-UPDATED "201408250000Z"
    ORGANIZATION "Information technologies Co.,Ltd"
    CONTACT-INFO
             "EMail:      service@copyright.com"
    DESCRIPTION
            "The MIB module is for optiway_expII_1.4.0."
    REVISION      "201408250000Z"
    DESCRIPTION
            "Modify some compile syntax error."
    ::= { enterprises 1013 }


systemManagement OBJECT IDENTIFIER ::= { optiwayExpII 1 } 
interfaces OBJECT IDENTIFIER ::= { optiwayExpII 2 }
boardPortManagement OBJECT IDENTIFIER ::= { optiwayExpII 3 }
traps OBJECT IDENTIFIER ::= { optiwayExpII 4 }

InterfaceIndex ::= TEXTUAL-CONVENTION
    DISPLAY-HINT "d"
    STATUS       current
    DESCRIPTION
            "A unique value, greater than zero, for each interface or
            interface sub-layer in the managed system.  It is
            recommended that values are assigned contiguously starting
            from 1.  The value for each interface sub-layer must remain
            constant at least from one re-initialization of the entity's
            network management system to the next re-initialization."
    SYNTAX       Integer32 (1..2147483647)

-- The systemManagement group --

platform OBJECT-TYPE
    SYNTAX      DisplayString (SIZE (0..255))
    MAX-ACCESS  read-only
    STATUS      current
    DESCRIPTION
            "platform"
    ::= { systemManagement 1 }


softwareVerion OBJECT-TYPE
    SYNTAX      DisplayString (SIZE (0..255))
    MAX-ACCESS  read-only
    STATUS      current
    DESCRIPTION
            "software verion."
    ::= { systemManagement 2 }
	
sysTime OBJECT-TYPE
    SYNTAX      DisplayString (SIZE (0..255))
    MAX-ACCESS  read-only
    STATUS      current
    DESCRIPTION
            "System Time."
    ::= { systemManagement 3 }
	
sysRunningTime OBJECT-TYPE
    SYNTAX      Integer32
    MAX-ACCESS  read-only
    STATUS      current
    DESCRIPTION
            "System running time. Unit is second."
    ::= { systemManagement 4 }
   
sysIp OBJECT-TYPE
    SYNTAX      DisplayString (SIZE (0..255))
    MAX-ACCESS  read-only
    STATUS      current
    DESCRIPTION
            "System Ip/Mask Addr."
    ::= { systemManagement 5 }

sysGateway OBJECT-TYPE
    SYNTAX      DisplayString (SIZE (0..255))
    MAX-ACCESS  read-only
    STATUS      current
    DESCRIPTION
            "System Gateway"
    ::= { systemManagement 6 }

-- cpuUtilizationTable --

cpuUtilizationTable OBJECT-TYPE
    SYNTAX      SEQUENCE OF CpuUtilizationEntry
    MAX-ACCESS  not-accessible
    STATUS      current
    DESCRIPTION
            "A list of all cpus's utilization."
    ::= { systemManagement 7 }  

cpuUtilizationEntry OBJECT-TYPE
    SYNTAX      CpuUtilizationEntry
    MAX-ACCESS  not-accessible
    STATUS      current
    DESCRIPTION
            "An entry contains a cpu's utilization."
    INDEX   { cpuIndex }
    ::= { cpuUtilizationTable 1 }

CpuUtilizationEntry ::=
    SEQUENCE {     
		cpuIndex                              Integer32,
		cpuUtilization5to30Second             Integer32,
		cpuUtilization1to5Minute              Integer32
    }  

cpuIndex OBJECT-TYPE
    SYNTAX      Integer32 (1..2147483647)
    MAX-ACCESS  not-accessible
    STATUS      current
    DESCRIPTION
            "A unique value, greater than zero, for each cpu."
    ::= { cpuUtilizationEntry 1 }

cpuUtilization5to30Second OBJECT-TYPE
    SYNTAX      Integer32 (0..100)
    MAX-ACCESS  read-only
    STATUS      current
    DESCRIPTION
            "Cpu utilization in 5 ~ 30 second. Unit is %."
    ::= { cpuUtilizationEntry 2 }

cpuUtilization1to5Minute OBJECT-TYPE
    SYNTAX      Integer32 (0..100)
    MAX-ACCESS  read-only
    STATUS      current
    DESCRIPTION
            "Cpu utilization in 1 ~ 5 minute. Unit is %."
    ::= { cpuUtilizationEntry 3 }


-- memoryOccupancyRateTable --

memoryOccupancyRateTable OBJECT-TYPE
    SYNTAX      SEQUENCE OF MemoryOccupancyRateEntry
    MAX-ACCESS  not-accessible
    STATUS      current
    DESCRIPTION
            "A list of all memories's occupancy rate."
    ::= { systemManagement 8 }  

memoryOccupancyRateEntry OBJECT-TYPE
    SYNTAX      MemoryOccupancyRateEntry
    MAX-ACCESS  not-accessible
    STATUS      current
    DESCRIPTION
            "An entry contains a memory's occupancy rate."
    INDEX   { memoryIndex }
    ::= { memoryOccupancyRateTable 1 }

MemoryOccupancyRateEntry ::=
    SEQUENCE {     
		memoryIndex                     Integer32,
		maxmemory                       Counter32,
		memoryOccupancyRate             Integer32
    } 

memoryIndex OBJECT-TYPE
    SYNTAX      Integer32 (1..2147483647)
    MAX-ACCESS  not-accessible
    STATUS      current
    DESCRIPTION
            "A unique value, greater than zero, for each memory."
    ::= { memoryOccupancyRateEntry 1 }

maxmemory OBJECT-TYPE
    SYNTAX      Counter32
    MAX-ACCESS  read-only
    STATUS      current
    DESCRIPTION
            "Max memory. Unit is MB."
    ::= { memoryOccupancyRateEntry 2 }

memoryOccupancyRate OBJECT-TYPE
    SYNTAX      Integer32 (0..100)
    MAX-ACCESS  read-only
    STATUS      current
    DESCRIPTION
            "Memory occupancy rate. Unit is %."
    ::= { memoryOccupancyRateEntry 3 }


-- powerTable --

powerTable OBJECT-TYPE
    SYNTAX      SEQUENCE OF PowerEntry
    MAX-ACCESS  not-accessible
    STATUS      current
    DESCRIPTION
            "A list of all powers's status."
    ::= { systemManagement 9 }  

powerEntry OBJECT-TYPE
    SYNTAX      PowerEntry
    MAX-ACCESS  not-accessible
    STATUS      current
    DESCRIPTION
            "An entry contains a power's status."
    INDEX   { powerIndex }
    ::= { powerTable 1 }

PowerEntry ::=
    SEQUENCE {     
		powerIndex                     Integer32,
		powerId                        Integer32,
		powerStatus                    INTEGER
    } 

powerIndex OBJECT-TYPE
    SYNTAX      Integer32 (1..2147483647)
    MAX-ACCESS  not-accessible
    STATUS      current
    DESCRIPTION
            "A unique value, greater than zero, for each power."
    ::= { powerEntry 1 }

powerId OBJECT-TYPE
    SYNTAX      Integer32
    MAX-ACCESS  read-only
    STATUS      current
    DESCRIPTION
            "Power id."
    ::= { powerEntry 2 }

powerStatus OBJECT-TYPE
    SYNTAX  INTEGER {
                normal(1),
                abnormal(2),
                offline(3)
            }
    MAX-ACCESS  read-only
    STATUS      current
    DESCRIPTION
            "Power status."
    ::= { powerEntry 3 }

-- airFanTable --
airFanTable OBJECT-TYPE
    SYNTAX      SEQUENCE OF AirFanEntry
    MAX-ACCESS  not-accessible
    STATUS      current
    DESCRIPTION
            "A list of all air fans's status."
    ::= { systemManagement 10 }  
	
airFanEntry OBJECT-TYPE
    SYNTAX      AirFanEntry
    MAX-ACCESS  not-accessible
    STATUS      current
    DESCRIPTION
            "An entry contains an air fan's status."
    INDEX   { airFanIndex }
    ::= { airFanTable 1 }

AirFanEntry ::=
    SEQUENCE {     
		airFanIndex                     Integer32,
		airFanId                        Integer32,
		airFanStatus                    INTEGER
    } 
	
airFanIndex OBJECT-TYPE
    SYNTAX      Integer32 (1..2147483647)
    MAX-ACCESS  not-accessible
    STATUS      current
    DESCRIPTION
            "A unique value, greater than zero, for each air fan."
    ::= { airFanEntry 1 }

airFanId OBJECT-TYPE
    SYNTAX      Integer32
    MAX-ACCESS  read-only
    STATUS      current
    DESCRIPTION
            "Air fan id."
    ::= { airFanEntry 2 }

airFanStatus OBJECT-TYPE
    SYNTAX  INTEGER {
                normal(1),
                abnormal(2),
                offline(3)
            }
    MAX-ACCESS  read-only
    STATUS      current
    DESCRIPTION
            "Air fan status."
    ::= { airFanEntry 3 }
    
    
-- The Interfaces group

-- InterfaceIndex contains the semantics of ifIndex and should be used
-- for any objects defined in other MIB modules that need these semantics.      

slotNumber  OBJECT-TYPE
    SYNTAX      Integer32
    MAX-ACCESS  read-only
    STATUS      current
    DESCRIPTION
            "The number of board present on this system."
    ::= { interfaces 1 }

slot1  OBJECT IDENTIFIER ::= { interfaces 2 } 
slot2  OBJECT IDENTIFIER ::= { interfaces 3 }
slot3  OBJECT IDENTIFIER ::= { interfaces 4 }
slot4  OBJECT IDENTIFIER ::= { interfaces 5 }
slot5  OBJECT IDENTIFIER ::= { interfaces 6 }
slot6  OBJECT IDENTIFIER ::= { interfaces 7 }
slot7  OBJECT IDENTIFIER ::= { interfaces 8 }
slot8  OBJECT IDENTIFIER ::= { interfaces 9 }
slot9  OBJECT IDENTIFIER ::= { interfaces 10 }
slot10 OBJECT IDENTIFIER ::= { interfaces 11 }
slot11 OBJECT IDENTIFIER ::= { interfaces 12 }
slot12 OBJECT IDENTIFIER ::= { interfaces 13 }
slot13 OBJECT IDENTIFIER ::= { interfaces 14 }
slot14 OBJECT IDENTIFIER ::= { interfaces 15 }
		
-- slot 1 --

-- slot1Table --

slot1Table OBJECT-TYPE
    SYNTAX      SEQUENCE OF Slot1Entry
    MAX-ACCESS  not-accessible
    STATUS      current
    DESCRIPTION
            "A list of all slot1Type's utilization."
    ::= { slot1 1 }  

slot1Entry OBJECT-TYPE
    SYNTAX      Slot1Entry
    MAX-ACCESS  not-accessible
    STATUS      current
    DESCRIPTION
            "An entry contains a slot1's utilization."
    INDEX   { slot1Index }
    ::= { slot1Table 1 }

Slot1Entry ::=
    SEQUENCE {     
		slot1Index                       Integer32,
		slot1Type                        DisplayString,
		slot1Status                      DisplayString,
		slot1Id                          Integer32
    }  

slot1Index OBJECT-TYPE
    SYNTAX      Integer32 (1..2147483647)
    MAX-ACCESS  not-accessible
    STATUS      current
    DESCRIPTION
            "A unique value, greater than zero, for each chassis`s slot1."
    ::= { slot1Entry 1 }

slot1Type OBJECT-TYPE
    SYNTAX      DisplayString (SIZE (0..255))
    MAX-ACCESS  read-only
    STATUS      current
    DESCRIPTION
            "the slot1Type of each chassis."
    ::= { slot1Entry 2 }

slot1Status OBJECT-TYPE
    SYNTAX      DisplayString (SIZE (0..255))
    MAX-ACCESS  read-only
    STATUS      current
    DESCRIPTION
            "A string to describe the board status." 
    ::= { slot1Entry 3 }   

slot1Id OBJECT-TYPE
    SYNTAX      Integer32
    MAX-ACCESS  read-only
    STATUS      current
    DESCRIPTION
            "slot id."
    ::= { slot1Entry 4 }

slot1Module OBJECT IDENTIFIER ::= { slot1 2 }

-- slot1ModuleTable --
slot1ModuleTable OBJECT-TYPE
    SYNTAX      SEQUENCE OF Slot1ModuleEntry
    MAX-ACCESS  not-accessible
    STATUS      current
    DESCRIPTION
            "A list of all slot1Module's utilization."
    ::= { slot1Module 1 }  

slot1ModuleEntry OBJECT-TYPE
    SYNTAX      Slot1ModuleEntry
    MAX-ACCESS  not-accessible
    STATUS      current
    DESCRIPTION
            "An entry contains a slot1Module's utilization."
    INDEX   { slot1ModuleIndex }
    ::= { slot1ModuleTable 1 }

Slot1ModuleEntry ::=
    SEQUENCE {     
		slot1ModuleIndex                       Integer32,
		slot1ModuleId                           DisplayString,  
		slot1ModuleIfNumber                     Integer32		
    } 

slot1ModuleIndex OBJECT-TYPE
    SYNTAX      Integer32 (1..2147483647)
    MAX-ACCESS  not-accessible
    STATUS      current
    DESCRIPTION
            "A unique value, greater than zero, for each chassis`s slot1."
    ::= { slot1ModuleEntry 1 }

slot1ModuleId OBJECT-TYPE
    SYNTAX      DisplayString (SIZE (0..32))
    MAX-ACCESS  read-only
    STATUS      current
    DESCRIPTION
            "the value of module`s id"
    ::= { slot1ModuleEntry 2 }
  
slot1ModuleIfNumber OBJECT-TYPE
    SYNTAX      Integer32(0..2147483647)
    MAX-ACCESS  read-only
    STATUS      current
    DESCRIPTION
            "The number of network interfaces (regardless of their
            current state) present on this system." 
    ::= { slot1ModuleEntry 3 } 
    
slot1ModuleIfTable OBJECT-TYPE
    SYNTAX      SEQUENCE OF Slot1ModuleIfEntry
    MAX-ACCESS  not-accessible
    STATUS      current
    DESCRIPTION
            "A list of interface entries.  The number of entries is
            given by the value of ifNumber."
    ::= { slot1Module 2 } 
    
slot1ModuleIfEntry OBJECT-TYPE
    SYNTAX      Slot1ModuleIfEntry
    MAX-ACCESS  not-accessible
    STATUS      current
    DESCRIPTION
            "An entry containing management information applicable to a
            particular interface."
    INDEX   { slot1ModuleifIndex }
    ::= { slot1ModuleIfTable 1 }
    
Slot1ModuleIfEntry ::=
    SEQUENCE {
        slot1ModuleifIndex                 InterfaceIndex,  
        slot1ModuleIfId                    DisplayString,  
        slot1ModuleifDescr                 DisplayString,           
        slot1ModuleifType                  IANAifType,   		
        slot1ModuleifMtu                   Integer32,                
        slot1ModuleifSpeed                 Counter64,               
        slot1ModuleifPhysAddress           PhysAddress,              
        slot1ModuleifAdminStatus           INTEGER,                  
        slot1ModuleifOperStatus            INTEGER,                  
        slot1ModuleifLastChange            TimeTicks,                
	slot1ModuleifInKbits   	           Counter64,
	slot1ModuleifOutKbits              Counter64,
        slot1ModuleifInOctets              Counter64,                
        slot1ModuleifInUcastPkts           Counter64,                
        slot1ModuleifInNUcastPkts          Counter64,  
        slot1ModuleifInDiscards            Counter64,
        slot1ModuleifInErrors              Counter64,
        slot1ModuleifInFcsErrorPkts        Counter64,
        slot1ModuleifInUnknownProtos       Counter64,	-- deprecated
        slot1ModuleifOutOctets             Counter64,
        slot1ModuleifOutUcastPkts          Counter64,
        slot1ModuleifOutNUcastPkts         Counter64,  -- deprecated
        slot1ModuleifOutDiscards           Counter64,
        slot1ModuleifOutErrors             Counter64,
        slot1ModuleifOutFcsErrorPkts       Counter64,
        slot1ModuleifOutQLen               Gauge32,    -- deprecated  
	 	slot1ModuleifInpps   	           Counter64,
		slot1ModuleifOutpps              Counter64,
        slot1ModuleifRxPower                DisplayString,        
        slot1ModuleifTxPower                DisplayString,        
        slot1ModuleifSpecific              OBJECT IDENTIFIER       
    }         

slot1ModuleifIndex OBJECT-TYPE
    SYNTAX      InterfaceIndex
    MAX-ACCESS  read-only
    STATUS      current
    DESCRIPTION
            "A unique value, greater than zero, for each interface.  It
            is recommended that values are assigned contiguously
            starting from 1.  The value for each interface sub-layer
            must remain constant at least from one re-initialization of
            the entity's network management system to the next re-
            initialization."
    ::= { slot1ModuleIfEntry 1 }
    
slot1ModuleIfId OBJECT-TYPE
    SYNTAX      DisplayString (SIZE (0..32))
    MAX-ACCESS  read-only
    STATUS      current
    DESCRIPTION
            "the value of module`s id"
    ::= { slot1ModuleIfEntry 2 }
    
slot1ModuleifDescr OBJECT-TYPE
    SYNTAX      DisplayString (SIZE (0..255))
    MAX-ACCESS  read-only
    STATUS      current
    DESCRIPTION
            "A textual string containing information about the
            interface.  This string should include the name of the
            manufacturer, the product name and the version of the
            interface hardware/software."
    ::= { slot1ModuleIfEntry 3 }
    
slot1ModuleifType OBJECT-TYPE
    SYNTAX      IANAifType
    MAX-ACCESS  read-only
    STATUS      current
    DESCRIPTION
            "The type of interface.  Additional values for ifType are
            assigned by the Internet Assigned Numbers Authority (IANA),
            through updating the syntax of the IANAifType textual
            convention."
    ::= { slot1ModuleIfEntry 4 }

slot1ModuleifMtu OBJECT-TYPE
    SYNTAX      Integer32(1..2147483647)
    MAX-ACCESS  read-only
    STATUS      current
    DESCRIPTION
            "The size of the largest packet which can be sent/received
            on the interface, specified in octets.  For interfaces that
            are used for transmitting network datagrams, this is the
            size of the largest network datagram that can be sent on the
            interface."
    ::= { slot1ModuleIfEntry 5 }

slot1ModuleifSpeed OBJECT-TYPE
    SYNTAX      Counter64
    MAX-ACCESS  read-only
    STATUS      current
    DESCRIPTION
            "An estimate of the interface's current bandwidth in bits
            per second.  For interfaces which do not vary in bandwidth
            or for those where no accurate estimation can be made, this
            object should contain the nominal bandwidth. For a sub-layer
            which has no concept of bandwidth, this object should be zero."
    ::= { slot1ModuleIfEntry 6 }

slot1ModuleifPhysAddress OBJECT-TYPE
    SYNTAX      PhysAddress
    MAX-ACCESS  read-only
    STATUS      current
    DESCRIPTION
            "The interface's address at its protocol sub-layer.  For
            example, for an 802.x interface, this object normally
            contains a MAC address.  The interface's media-specific MIB
            must define the bit and byte ordering and the format of the
            value of this object.  For interfaces which do not have such
            an address (e.g., a serial line), this object should contain
            an octet string of zero length."
    ::= { slot1ModuleIfEntry 7 }
    
slot1ModuleifAdminStatus OBJECT-TYPE
    SYNTAX  INTEGER {
                up(1),       -- ready to pass packets
                down(2),
                testing(3)   -- in some test mode
            }
    MAX-ACCESS  read-write
    STATUS      current
    DESCRIPTION
            "The desired state of the interface.  The testing(3) state
            indicates that no operational packets can be passed.  When a
            managed system initializes, all interfaces start with
            ifAdminStatus in the down(2) state.  As a result of either
            explicit management action or per configuration information
            retained by the managed system, ifAdminStatus is then
            changed to either the up(1) or testing(3) states (or remains
            in the down(2) state)."
    ::= { slot1ModuleIfEntry 8 }

slot1ModuleifOperStatus OBJECT-TYPE
    SYNTAX  INTEGER {
                up(1),        -- ready to pass packets
                down(2),
                testing(3),   -- in some test mode
                unknown(4),   -- status can not be determined
                              -- for some reason.
                dormant(5),
                notPresent(6),    -- some component is missing
                lowerLayerDown(7) -- down due to state of
                                  -- lower-layer interface(s)
            }
    MAX-ACCESS  read-only
    STATUS      current
    DESCRIPTION
            "The current operational state of the interface.  The
            testing(3) state indicates that no operational packets can
            be passed.  If ifAdminStatus is down(2) then ifOperStatus
            should be down(2).  If ifAdminStatus is changed to up(1)
            then ifOperStatus should change to up(1) if the interface is
            ready to transmit and receive network traffic; it should
            change to dormant(5) if the interface is waiting for
            external actions (such as a serial line waiting for an
            incoming connection); it should remain in the down(2) state
            if and only if there is a fault that prevents it from going
            to the up(1) state; it should remain in the notPresent(6)
            state if the interface has missing (typically, hardware)
            components."
    ::= { slot1ModuleIfEntry 9 }

slot1ModuleifLastChange OBJECT-TYPE
    SYNTAX      TimeTicks
    MAX-ACCESS  read-only
    STATUS      current
    DESCRIPTION
            "The value of sysUpTime at the time the interface entered
            its current operational state.  If the current state was
            entered prior to the last re-initialization of the local
            network management subsystem, then this object contains a
            zero value."
    ::= { slot1ModuleIfEntry 10 }

slot1ModuleifInKbits OBJECT-TYPE
    SYNTAX      Counter64
    MAX-ACCESS  read-only
    STATUS      current
    DESCRIPTION
            "The real time rate received on the interface, in Kbits
	    format.

            Discontinuities in the value of this counter can occur at
            re-initialization of the management system, and at other
            times as indicated by the value of
            ifCounterDiscontinuityTime."
    ::= { slot1ModuleIfEntry 11 }

slot1ModuleifOutKbits OBJECT-TYPE
    SYNTAX      Counter64
    MAX-ACCESS  read-only
    STATUS      current
    DESCRIPTION
            "The real time rate send on the interface, in Kbits
	    format.

            Discontinuities in the value of this counter can occur at
            re-initialization of the management system, and at other
            times as indicated by the value of
            ifCounterDiscontinuityTime."
    ::= { slot1ModuleIfEntry 12 }

slot1ModuleifInOctets OBJECT-TYPE
    SYNTAX      Counter64
    MAX-ACCESS  read-only
    STATUS      current
    DESCRIPTION
            "The total number of octets received on the interface,
            including framing characters.

            Discontinuities in the value of this counter can occur at
            re-initialization of the management system, and at other
            times as indicated by the value of
            ifCounterDiscontinuityTime."
    ::= { slot1ModuleIfEntry 13 }

slot1ModuleifInUcastPkts OBJECT-TYPE
    SYNTAX      Counter64
    MAX-ACCESS  read-only
    STATUS      current
    DESCRIPTION
            "The number of packets, delivered by this sub-layer to a
            higher (sub-)layer, which were not addressed to a multicast
            or broadcast address at this sub-layer.

            Discontinuities in the value of this counter can occur at
            re-initialization of the management system, and at other
            times as indicated by the value of
            ifCounterDiscontinuityTime."
    ::= { slot1ModuleIfEntry 14 }

slot1ModuleifInNUcastPkts OBJECT-TYPE
    SYNTAX  Counter64
    MAX-ACCESS  read-only
    STATUS      current
    DESCRIPTION
            "The number of packets, delivered by this sub-layer to a
            higher (sub-)layer, which were addressed to a multicast or
            broadcast address at this sub-layer.

            Discontinuities in the value of this counter can occur at
            re-initialization of the management system, and at other
            times as indicated by the value of
            ifCounterDiscontinuityTime.

            This object is deprecated in favour of ifInMulticastPkts and
            ifInBroadcastPkts."
    ::= { slot1ModuleIfEntry 15 }

slot1ModuleifInDiscards OBJECT-TYPE
    SYNTAX      Counter64
    MAX-ACCESS  read-only
    STATUS      current
    DESCRIPTION
            "The number of inbound packets which were chosen to be
            discarded even though no errors had been detected to prevent

            their being deliverable to a higher-layer protocol.  One
            possible reason for discarding such a packet could be to
            free up buffer space.

            Discontinuities in the value of this counter can occur at
            re-initialization of the management system, and at other
            times as indicated by the value of
            ifCounterDiscontinuityTime."
    ::= { slot1ModuleIfEntry 16 }

slot1ModuleifInErrors OBJECT-TYPE
    SYNTAX      Counter64
    MAX-ACCESS  read-only
    STATUS      current
    DESCRIPTION
            "For packet-oriented interfaces, the number of inbound
            packets that contained errors preventing them from being
            deliverable to a higher-layer protocol.  For character-
            oriented or fixed-length interfaces, the number of inbound
            transmission units that contained errors preventing them
            from being deliverable to a higher-layer protocol.

            Discontinuities in the value of this counter can occur at
            re-initialization of the management system, and at other
            times as indicated by the value of
            ifCounterDiscontinuityTime."
    ::= { slot1ModuleIfEntry 17 }

slot1ModuleifInFcsErrorPkts OBJECT-TYPE
    SYNTAX      Counter64
    MAX-ACCESS  read-only
    STATUS      current
    DESCRIPTION
            "FCS error pakets."
    ::= { slot1ModuleIfEntry 18 }

slot1ModuleifInUnknownProtos OBJECT-TYPE
    SYNTAX      Counter64
    MAX-ACCESS  read-only
    STATUS      current
    DESCRIPTION
            "For packet-oriented interfaces, the number of packets
            received via the interface which were discarded because of
            an unknown or unsupported protocol.  For character-oriented
            or fixed-length interfaces that support protocol
            multiplexing the number of transmission units received via
            the interface which were discarded because of an unknown or
            unsupported protocol.  For any interface that does not
            support protocol multiplexing, this counter will always be
            0.

            Discontinuities in the value of this counter can occur at
            re-initialization of the management system, and at other
            times as indicated by the value of
            ifCounterDiscontinuityTime."
    ::= { slot1ModuleIfEntry 19 }

slot1ModuleifOutOctets OBJECT-TYPE
    SYNTAX      Counter64
    MAX-ACCESS  read-only
    STATUS      current
    DESCRIPTION
            "The total number of octets transmitted out of the
            interface, including framing characters.

            Discontinuities in the value of this counter can occur at
            re-initialization of the management system, and at other
            times as indicated by the value of
            ifCounterDiscontinuityTime."
    ::= { slot1ModuleIfEntry 20 }

slot1ModuleifOutUcastPkts OBJECT-TYPE
    SYNTAX      Counter64
    MAX-ACCESS  read-only
    STATUS      current
    DESCRIPTION
            "The total number of packets that higher-level protocols
            requested be transmitted, and which were not addressed to a
            multicast or broadcast address at this sub-layer, including
            those that were discarded or not sent.

            Discontinuities in the value of this counter can occur at
            re-initialization of the management system, and at other
            times as indicated by the value of
            ifCounterDiscontinuityTime."
    ::= { slot1ModuleIfEntry 21 }

slot1ModuleifOutNUcastPkts OBJECT-TYPE
    SYNTAX      Counter64
    MAX-ACCESS  read-only
    STATUS      deprecated
    DESCRIPTION
            "The total number of packets that higher-level protocols
            requested be transmitted, and which were addressed to a
            multicast or broadcast address at this sub-layer, including
            those that were discarded or not sent.

            Discontinuities in the value of this counter can occur at
            re-initialization of the management system, and at other
            times as indicated by the value of
            ifCounterDiscontinuityTime.

            This object is deprecated in favour of ifOutMulticastPkts
            and ifOutBroadcastPkts."
    ::= { slot1ModuleIfEntry 22 }

slot1ModuleifOutDiscards OBJECT-TYPE
    SYNTAX      Counter64
    MAX-ACCESS  read-only
    STATUS      current
    DESCRIPTION
            "The number of outbound packets which were chosen to be
            discarded even though no errors had been detected to prevent
            their being transmitted.  One possible reason for discarding
            such a packet could be to free up buffer space.

            Discontinuities in the value of this counter can occur at
            re-initialization of the management system, and at other
            times as indicated by the value of
            ifCounterDiscontinuityTime."
    ::= { slot1ModuleIfEntry 23 }

slot1ModuleifOutErrors OBJECT-TYPE
    SYNTAX      Counter64
    MAX-ACCESS  read-only
    STATUS      current
    DESCRIPTION
            "For packet-oriented interfaces, the number of outbound
            packets that could not be transmitted because of errors.
            For character-oriented or fixed-length interfaces, the
            number of outbound transmission units that could not be
            transmitted because of errors.

            Discontinuities in the value of this counter can occur at
            re-initialization of the management system, and at other
            times as indicated by the value of
            ifCounterDiscontinuityTime."
    ::= { slot1ModuleIfEntry 24 }

slot1ModuleifOutFcsErrorPkts OBJECT-TYPE
    SYNTAX      Counter64
    MAX-ACCESS  read-only
    STATUS      current
    DESCRIPTION
            "FCS error pakets."
    ::= { slot1ModuleIfEntry 25 }

slot1ModuleifOutQLen OBJECT-TYPE
    SYNTAX      Gauge32
    MAX-ACCESS  read-only
    STATUS      deprecated
    DESCRIPTION
            "The length of the output packet queue (in packets)."
    ::= { slot1ModuleIfEntry 26 }
    
slot1ModuleifInpps OBJECT-TYPE
    SYNTAX      Counter64
    MAX-ACCESS  read-only
    STATUS      current
    DESCRIPTION
            "The real time rate received on the interface, in pps
	    format.

            Discontinuities in the value of this counter can occur at
            re-initialization of the management system, and at other
            times as indicated by the value of
            ifCounterDiscontinuityTime."
    ::= { slot1ModuleIfEntry 27 }

slot1ModuleifOutpps OBJECT-TYPE
    SYNTAX      Counter64
    MAX-ACCESS  read-only
    STATUS      current
    DESCRIPTION
            "The real time rate send on the interface, in pps
	    format.

            Discontinuities in the value of this counter can occur at
            re-initialization of the management system, and at other
            times as indicated by the value of
            ifCounterDiscontinuityTime."
    ::= { slot1ModuleIfEntry 28 }

slot1ModuleifRxPower OBJECT-TYPE
    SYNTAX      DisplayString (SIZE (0..255))
    MAX-ACCESS  read-only
    STATUS      current
    DESCRIPTION
            "the value of interface's received power, in dbm format."
    ::= { slot1ModuleIfEntry 29 }
    
slot1ModuleifTxPower OBJECT-TYPE
    SYNTAX      DisplayString (SIZE (0..255))
    MAX-ACCESS  read-only
    STATUS      current
    DESCRIPTION
            "the value of interface's send power, in dbm format."
    ::= { slot1ModuleIfEntry 30 }
        
slot1ModuleifSpecific OBJECT-TYPE
    SYNTAX      OBJECT IDENTIFIER
    MAX-ACCESS  read-only
    STATUS      deprecated
    DESCRIPTION
            "A reference to MIB definitions specific to the particular
            media being used to realize the interface.  It is

            recommended that this value point to an instance of a MIB
            object in the media-specific MIB, i.e., that this object
            have the semantics associated with the InstancePointer
            textual convention defined in RFC 2579.  In fact, it is
            recommended that the media-specific MIB specify what value
            ifSpecific should/can take for values of ifType.  If no MIB
            definitions specific to the particular media are available,
            the value should be set to the OBJECT IDENTIFIER { 0 0 }."
    ::= { slot1ModuleIfEntry 31 }  
    
-- slot 2 --

-- slot2Table --

slot2Table OBJECT-TYPE
    SYNTAX      SEQUENCE OF Slot2Entry
    MAX-ACCESS  not-accessible
    STATUS      current
    DESCRIPTION
            "A list of all slot2Type's utilization."
    ::= { slot2 1 }  

slot2Entry OBJECT-TYPE
    SYNTAX      Slot2Entry
    MAX-ACCESS  not-accessible
    STATUS      current
    DESCRIPTION
            "An entry contains a slot2's utilization."
    INDEX   { slot2Index }
    ::= { slot2Table 1 }

Slot2Entry ::=
    SEQUENCE {     
		slot2Index                       Integer32,
		slot2Type                        DisplayString,
		slot2Status                      DisplayString,	
		slot2Id                          Integer32
    }  

slot2Index OBJECT-TYPE
    SYNTAX      Integer32 (1..2147483647)
    MAX-ACCESS  not-accessible
    STATUS      current
    DESCRIPTION
            "A unique value, greater than zero, for each chassis`s slot2."
    ::= { slot2Entry 1 }

slot2Type OBJECT-TYPE
    SYNTAX      DisplayString (SIZE (0..255))
    MAX-ACCESS  read-only
    STATUS      current
    DESCRIPTION
            "the slot2Type of each chassis."
    ::= { slot2Entry 2 }

slot2Status OBJECT-TYPE
    SYNTAX      DisplayString (SIZE (0..255))
    MAX-ACCESS  read-only
    STATUS      current
    DESCRIPTION
            "A string to describe the board status." 
    ::= { slot2Entry 3 }   

slot2Id OBJECT-TYPE
    SYNTAX      Integer32
    MAX-ACCESS  read-only
    STATUS      current
    DESCRIPTION
            "slot id."
    ::= { slot2Entry 4 }

slot2Module OBJECT IDENTIFIER ::= { slot2 2 }

-- slot2ModuleTable --
slot2ModuleTable OBJECT-TYPE
    SYNTAX      SEQUENCE OF Slot2ModuleEntry
    MAX-ACCESS  not-accessible
    STATUS      current
    DESCRIPTION
            "A list of all slot2Module's utilization."
    ::= { slot2Module 1 }  

slot2ModuleEntry OBJECT-TYPE
    SYNTAX      Slot2ModuleEntry
    MAX-ACCESS  not-accessible
    STATUS      current
    DESCRIPTION
            "An entry contains a slot2Module's utilization."
    INDEX   { slot2ModuleIndex }
    ::= { slot2ModuleTable 1 }

Slot2ModuleEntry ::=
    SEQUENCE {     
		slot2ModuleIndex                       Integer32,
		slot2ModuleId                           DisplayString,  
		slot2ModuleIfNumber                     Integer32		
    } 

slot2ModuleIndex OBJECT-TYPE
    SYNTAX      Integer32 (1..2147483647)
    MAX-ACCESS  not-accessible
    STATUS      current
    DESCRIPTION
            "A unique value, greater than zero, for each chassis`s slot2."
    ::= { slot2ModuleEntry 1 }

slot2ModuleId OBJECT-TYPE
    SYNTAX      DisplayString (SIZE (0..32))
    MAX-ACCESS  read-only
    STATUS      current
    DESCRIPTION
            "the value of module`s id"
    ::= { slot2ModuleEntry 2 }
  
slot2ModuleIfNumber OBJECT-TYPE
    SYNTAX      Integer32(0..2147483647)
    MAX-ACCESS  read-only
    STATUS      current
    DESCRIPTION
            "The number of network interfaces (regardless of their
            current state) present on this system." 
    ::= { slot2ModuleEntry 3 } 
    
slot2ModuleIfTable OBJECT-TYPE
    SYNTAX      SEQUENCE OF Slot2ModuleIfEntry
    MAX-ACCESS  not-accessible
    STATUS      current
    DESCRIPTION
            "A list of interface entries.  The number of entries is
            given by the value of ifNumber."
    ::= { slot2Module 2 } 
    
slot2ModuleIfEntry OBJECT-TYPE
    SYNTAX      Slot2ModuleIfEntry
    MAX-ACCESS  not-accessible
    STATUS      current
    DESCRIPTION
            "An entry containing management information applicable to a
            particular interface."
    INDEX   { slot2ModuleifIndex }
    ::= { slot2ModuleIfTable 1 }
    
Slot2ModuleIfEntry ::=
    SEQUENCE {
        slot2ModuleifIndex                 InterfaceIndex,  
        slot2ModuleIfId                    DisplayString,  
        slot2ModuleifDescr                 DisplayString,           
        slot2ModuleifType                  IANAifType,   		
        slot2ModuleifMtu                   Integer32,                
        slot2ModuleifSpeed                 Counter64,               
        slot2ModuleifPhysAddress           PhysAddress,              
        slot2ModuleifAdminStatus           INTEGER,                  
        slot2ModuleifOperStatus            INTEGER,                  
        slot2ModuleifLastChange            TimeTicks,                
	slot2ModuleifInKbits   	           Counter64,
	slot2ModuleifOutKbits              Counter64,
        slot2ModuleifInOctets              Counter64,                
        slot2ModuleifInUcastPkts           Counter64,                
        slot2ModuleifInNUcastPkts          Counter64,   
        slot2ModuleifInDiscards            Counter64,
        slot2ModuleifInErrors              Counter64,
        slot2ModuleifInFcsErrorPkts        Counter64,
        slot2ModuleifInUnknownProtos       Counter64,	-- deprecated
        slot2ModuleifOutOctets             Counter64,
        slot2ModuleifOutUcastPkts          Counter64,
        slot2ModuleifOutNUcastPkts         Counter64,  -- deprecated
        slot2ModuleifOutDiscards           Counter64,
        slot2ModuleifOutErrors             Counter64,
        slot2ModuleifOutFcsErrorPkts       Counter64,
        slot2ModuleifOutQLen               Gauge32,    -- deprecated  
	    slot2ModuleifInpps   	           Counter64,
	    slot2ModuleifOutpps              Counter64,       
        slot2ModuleifRxPower                DisplayString,
        slot2ModuleifTxPower                DisplayString, 
        slot2ModuleifSpecific              OBJECT IDENTIFIER
    }         

slot2ModuleifIndex OBJECT-TYPE
    SYNTAX      InterfaceIndex
    MAX-ACCESS  read-only
    STATUS      current
    DESCRIPTION
            "A unique value, greater than zero, for each interface.  It
            is recommended that values are assigned contiguously
            starting from 1.  The value for each interface sub-layer
            must remain constant at least from one re-initialization of
            the entity's network management system to the next re-
            initialization."
    ::= { slot2ModuleIfEntry 1 }
    
slot2ModuleIfId OBJECT-TYPE
    SYNTAX      DisplayString (SIZE (0..32))
    MAX-ACCESS  read-only
    STATUS      current
    DESCRIPTION
            "the value of module`s id"
    ::= { slot2ModuleIfEntry 2 }
    
slot2ModuleifDescr OBJECT-TYPE
    SYNTAX      DisplayString (SIZE (0..255))
    MAX-ACCESS  read-only
    STATUS      current
    DESCRIPTION
            "A textual string containing information about the
            interface.  This string should include the name of the
            manufacturer, the product name and the version of the
            interface hardware/software."
    ::= { slot2ModuleIfEntry 3 }
    
slot2ModuleifType OBJECT-TYPE
    SYNTAX      IANAifType
    MAX-ACCESS  read-only
    STATUS      current
    DESCRIPTION
            "The type of interface.  Additional values for ifType are
            assigned by the Internet Assigned Numbers Authority (IANA),
            through updating the syntax of the IANAifType textual
            convention."
    ::= { slot2ModuleIfEntry 4 }

slot2ModuleifMtu OBJECT-TYPE
    SYNTAX      Integer32(1..2147483647)
    MAX-ACCESS  read-only
    STATUS      current
    DESCRIPTION
            "The size of the largest packet which can be sent/received
            on the interface, specified in octets.  For interfaces that
            are used for transmitting network datagrams, this is the
            size of the largest network datagram that can be sent on the
            interface."
    ::= { slot2ModuleIfEntry 5 }

slot2ModuleifSpeed OBJECT-TYPE
    SYNTAX      Counter64
    MAX-ACCESS  read-only
    STATUS      current
    DESCRIPTION
            "An estimate of the interface's current bandwidth in bits
            per second.  For interfaces which do not vary in bandwidth
            or for those where no accurate estimation can be made, this
            object should contain the nominal bandwidth. For a sub-layer
            which has no concept of bandwidth, this object should be zero."
    ::= { slot2ModuleIfEntry 6 }

slot2ModuleifPhysAddress OBJECT-TYPE
    SYNTAX      PhysAddress
    MAX-ACCESS  read-only
    STATUS      current
    DESCRIPTION
            "The interface's address at its protocol sub-layer.  For
            example, for an 802.x interface, this object normally
            contains a MAC address.  The interface's media-specific MIB
            must define the bit and byte ordering and the format of the
            value of this object.  For interfaces which do not have such
            an address (e.g., a serial line), this object should contain
            an octet string of zero length."
    ::= { slot2ModuleIfEntry 7 }
    
slot2ModuleifAdminStatus OBJECT-TYPE
    SYNTAX  INTEGER {
                up(1),       -- ready to pass packets
                down(2),
                testing(3)   -- in some test mode
            }
    MAX-ACCESS  read-write
    STATUS      current
    DESCRIPTION
            "The desired state of the interface.  The testing(3) state
            indicates that no operational packets can be passed.  When a
            managed system initializes, all interfaces start with
            ifAdminStatus in the down(2) state.  As a result of either
            explicit management action or per configuration information
            retained by the managed system, ifAdminStatus is then
            changed to either the up(1) or testing(3) states (or remains
            in the down(2) state)."
    ::= { slot2ModuleIfEntry 8 }

slot2ModuleifOperStatus OBJECT-TYPE
    SYNTAX  INTEGER {
                up(1),        -- ready to pass packets
                down(2),
                testing(3),   -- in some test mode
                unknown(4),   -- status can not be determined
                              -- for some reason.
                dormant(5),
                notPresent(6),    -- some component is missing
                lowerLayerDown(7) -- down due to state of
                                  -- lower-layer interface(s)
            }
    MAX-ACCESS  read-only
    STATUS      current
    DESCRIPTION
            "The current operational state of the interface.  The
            testing(3) state indicates that no operational packets can
            be passed.  If ifAdminStatus is down(2) then ifOperStatus
            should be down(2).  If ifAdminStatus is changed to up(1)
            then ifOperStatus should change to up(1) if the interface is
            ready to transmit and receive network traffic; it should
            change to dormant(5) if the interface is waiting for
            external actions (such as a serial line waiting for an
            incoming connection); it should remain in the down(2) state
            if and only if there is a fault that prevents it from going
            to the up(1) state; it should remain in the notPresent(6)
            state if the interface has missing (typically, hardware)
            components."
    ::= { slot2ModuleIfEntry 9 }

slot2ModuleifLastChange OBJECT-TYPE
    SYNTAX      TimeTicks
    MAX-ACCESS  read-only
    STATUS      current
    DESCRIPTION
            "The value of sysUpTime at the time the interface entered
            its current operational state.  If the current state was
            entered prior to the last re-initialization of the local
            network management subsystem, then this object contains a
            zero value."
    ::= { slot2ModuleIfEntry 10 }

slot2ModuleifInKbits OBJECT-TYPE
    SYNTAX      Counter64
    MAX-ACCESS  read-only
    STATUS      current
    DESCRIPTION
            "The real time rate received on the interface, in Kbits
	    format.

            Discontinuities in the value of this counter can occur at
            re-initialization of the management system, and at other
            times as indicated by the value of
            ifCounterDiscontinuityTime."
    ::= { slot2ModuleIfEntry 11 }

slot2ModuleifOutKbits OBJECT-TYPE
    SYNTAX      Counter64
    MAX-ACCESS  read-only
    STATUS      current
    DESCRIPTION
            "The real time rate send on the interface, in Kbits
	    format.

            Discontinuities in the value of this counter can occur at
            re-initialization of the management system, and at other
            times as indicated by the value of
            ifCounterDiscontinuityTime."
    ::= { slot2ModuleIfEntry 12 }

slot2ModuleifInOctets OBJECT-TYPE
    SYNTAX      Counter64
    MAX-ACCESS  read-only
    STATUS      current
    DESCRIPTION
            "The total number of octets received on the interface,
            including framing characters.

            Discontinuities in the value of this counter can occur at
            re-initialization of the management system, and at other
            times as indicated by the value of
            ifCounterDiscontinuityTime."
    ::= { slot2ModuleIfEntry 13 }

slot2ModuleifInUcastPkts OBJECT-TYPE
    SYNTAX      Counter64
    MAX-ACCESS  read-only
    STATUS      current
    DESCRIPTION
            "The number of packets, delivered by this sub-layer to a
            higher (sub-)layer, which were not addressed to a multicast
            or broadcast address at this sub-layer.

            Discontinuities in the value of this counter can occur at
            re-initialization of the management system, and at other
            times as indicated by the value of
            ifCounterDiscontinuityTime."
    ::= { slot2ModuleIfEntry 14 }

slot2ModuleifInNUcastPkts OBJECT-TYPE
    SYNTAX  Counter64
    MAX-ACCESS  read-only
    STATUS      current
    DESCRIPTION
            "The number of packets, delivered by this sub-layer to a
            higher (sub-)layer, which were addressed to a multicast or
            broadcast address at this sub-layer.

            Discontinuities in the value of this counter can occur at
            re-initialization of the management system, and at other
            times as indicated by the value of
            ifCounterDiscontinuityTime.

            This object is deprecated in favour of ifInMulticastPkts and
            ifInBroadcastPkts."
    ::= { slot2ModuleIfEntry 15 }

slot2ModuleifInDiscards OBJECT-TYPE
    SYNTAX      Counter64
    MAX-ACCESS  read-only
    STATUS      current
    DESCRIPTION
            "The number of inbound packets which were chosen to be
            discarded even though no errors had been detected to prevent

            their being deliverable to a higher-layer protocol.  One
            possible reason for discarding such a packet could be to
            free up buffer space.

            Discontinuities in the value of this counter can occur at
            re-initialization of the management system, and at other
            times as indicated by the value of
            ifCounterDiscontinuityTime."
    ::= { slot2ModuleIfEntry 16 }

slot2ModuleifInErrors OBJECT-TYPE
    SYNTAX      Counter64
    MAX-ACCESS  read-only
    STATUS      current
    DESCRIPTION
            "For packet-oriented interfaces, the number of inbound
            packets that contained errors preventing them from being
            deliverable to a higher-layer protocol.  For character-
            oriented or fixed-length interfaces, the number of inbound
            transmission units that contained errors preventing them
            from being deliverable to a higher-layer protocol.

            Discontinuities in the value of this counter can occur at
            re-initialization of the management system, and at other
            times as indicated by the value of
            ifCounterDiscontinuityTime."
    ::= { slot2ModuleIfEntry 17 }

slot2ModuleifInFcsErrorPkts OBJECT-TYPE
    SYNTAX      Counter64
    MAX-ACCESS  read-only
    STATUS      current
    DESCRIPTION
            "FCS error pakets."
    ::= { slot2ModuleIfEntry 18 }

slot2ModuleifInUnknownProtos OBJECT-TYPE
    SYNTAX      Counter64
    MAX-ACCESS  read-only
    STATUS      current
    DESCRIPTION
            "For packet-oriented interfaces, the number of packets
            received via the interface which were discarded because of
            an unknown or unsupported protocol.  For character-oriented
            or fixed-length interfaces that support protocol
            multiplexing the number of transmission units received via
            the interface which were discarded because of an unknown or
            unsupported protocol.  For any interface that does not
            support protocol multiplexing, this counter will always be
            0.

            Discontinuities in the value of this counter can occur at
            re-initialization of the management system, and at other
            times as indicated by the value of
            ifCounterDiscontinuityTime."
    ::= { slot2ModuleIfEntry 19 }

slot2ModuleifOutOctets OBJECT-TYPE
    SYNTAX      Counter64
    MAX-ACCESS  read-only
    STATUS      current
    DESCRIPTION
            "The total number of octets transmitted out of the
            interface, including framing characters.

            Discontinuities in the value of this counter can occur at
            re-initialization of the management system, and at other
            times as indicated by the value of
            ifCounterDiscontinuityTime."
    ::= { slot2ModuleIfEntry 20 }

slot2ModuleifOutUcastPkts OBJECT-TYPE
    SYNTAX      Counter64
    MAX-ACCESS  read-only
    STATUS      current
    DESCRIPTION
            "The total number of packets that higher-level protocols
            requested be transmitted, and which were not addressed to a
            multicast or broadcast address at this sub-layer, including
            those that were discarded or not sent.

            Discontinuities in the value of this counter can occur at
            re-initialization of the management system, and at other
            times as indicated by the value of
            ifCounterDiscontinuityTime."
    ::= { slot2ModuleIfEntry 21 }

slot2ModuleifOutNUcastPkts OBJECT-TYPE
    SYNTAX      Counter64
    MAX-ACCESS  read-only
    STATUS      deprecated
    DESCRIPTION
            "The total number of packets that higher-level protocols
            requested be transmitted, and which were addressed to a
            multicast or broadcast address at this sub-layer, including
            those that were discarded or not sent.

            Discontinuities in the value of this counter can occur at
            re-initialization of the management system, and at other
            times as indicated by the value of
            ifCounterDiscontinuityTime.

            This object is deprecated in favour of ifOutMulticastPkts
            and ifOutBroadcastPkts."
    ::= { slot2ModuleIfEntry 22 }

slot2ModuleifOutDiscards OBJECT-TYPE
    SYNTAX      Counter64
    MAX-ACCESS  read-only
    STATUS      current
    DESCRIPTION
            "The number of outbound packets which were chosen to be
            discarded even though no errors had been detected to prevent
            their being transmitted.  One possible reason for discarding
            such a packet could be to free up buffer space.

            Discontinuities in the value of this counter can occur at
            re-initialization of the management system, and at other
            times as indicated by the value of
            ifCounterDiscontinuityTime."
    ::= { slot2ModuleIfEntry 23 }

slot2ModuleifOutErrors OBJECT-TYPE
    SYNTAX      Counter64
    MAX-ACCESS  read-only
    STATUS      current
    DESCRIPTION
            "For packet-oriented interfaces, the number of outbound
            packets that could not be transmitted because of errors.
            For character-oriented or fixed-length interfaces, the
            number of outbound transmission units that could not be
            transmitted because of errors.

            Discontinuities in the value of this counter can occur at
            re-initialization of the management system, and at other
            times as indicated by the value of
            ifCounterDiscontinuityTime."
    ::= { slot2ModuleIfEntry 24 }

slot2ModuleifOutFcsErrorPkts OBJECT-TYPE
    SYNTAX      Counter64
    MAX-ACCESS  read-only
    STATUS      current
    DESCRIPTION
            "FCS error pakets."
    ::= { slot2ModuleIfEntry 25 }

slot2ModuleifOutQLen OBJECT-TYPE
    SYNTAX      Gauge32
    MAX-ACCESS  read-only
    STATUS      deprecated
    DESCRIPTION
            "The length of the output packet queue (in packets)."
    ::= { slot2ModuleIfEntry 26 }
    
slot2ModuleifInpps OBJECT-TYPE
    SYNTAX      Counter64
    MAX-ACCESS  read-only
    STATUS      current
    DESCRIPTION
            "The real time rate received on the interface, in pps
	    format.

            Discontinuities in the value of this counter can occur at
            re-initialization of the management system, and at other
            times as indicated by the value of
            ifCounterDiscontinuityTime."
    ::= { slot2ModuleIfEntry 27 }

slot2ModuleifOutpps OBJECT-TYPE
    SYNTAX      Counter64
    MAX-ACCESS  read-only
    STATUS      current
    DESCRIPTION
            "The real time rate send on the interface, in pps
	    format.

            Discontinuities in the value of this counter can occur at
            re-initialization of the management system, and at other
            times as indicated by the value of
            ifCounterDiscontinuityTime."
    ::= { slot2ModuleIfEntry 28 }

slot2ModuleifRxPower OBJECT-TYPE
    SYNTAX      DisplayString (SIZE (0..255))
    MAX-ACCESS  read-only
    STATUS      current
    DESCRIPTION
            "the value of interface's received power, in dbm format."
    ::= { slot2ModuleIfEntry 29 }
    
slot2ModuleifTxPower OBJECT-TYPE
    SYNTAX      DisplayString (SIZE (0..255))
    MAX-ACCESS  read-only
    STATUS      current
    DESCRIPTION
            "the value of interface's send power, in dbm format."
    ::= { slot2ModuleIfEntry 30 }

slot2ModuleifSpecific OBJECT-TYPE
    SYNTAX      OBJECT IDENTIFIER
    MAX-ACCESS  read-only
    STATUS      deprecated
    DESCRIPTION
            "A reference to MIB definitions specific to the particular
            media being used to realize the interface.  It is

            recommended that this value point to an instance of a MIB
            object in the media-specific MIB, i.e., that this object
            have the semantics associated with the InstancePointer
            textual convention defined in RFC 2579.  In fact, it is
            recommended that the media-specific MIB specify what value
            ifSpecific should/can take for values of ifType.  If no MIB
            definitions specific to the particular media are available,
            the value should be set to the OBJECT IDENTIFIER { 0 0 }."
    ::= { slot2ModuleIfEntry 31 }  
    
-- slot 3 --

-- slot3Table --

slot3Table OBJECT-TYPE
    SYNTAX      SEQUENCE OF Slot3Entry
    MAX-ACCESS  not-accessible
    STATUS      current
    DESCRIPTION
            "A list of all slot3Type's utilization."
    ::= { slot3 1 }  

slot3Entry OBJECT-TYPE
    SYNTAX      Slot3Entry
    MAX-ACCESS  not-accessible
    STATUS      current
    DESCRIPTION
            "An entry contains a slot3's utilization."
    INDEX   { slot3Index }
    ::= { slot3Table 1 }

Slot3Entry ::=
    SEQUENCE {     
		slot3Index                       Integer32,
		slot3Type                        DisplayString,
		slot3Status                      DisplayString,
		slot3Id                          Integer32
    }  

slot3Index OBJECT-TYPE
    SYNTAX      Integer32 (1..2147483647)
    MAX-ACCESS  not-accessible
    STATUS      current
    DESCRIPTION
            "A unique value, greater than zero, for each chassis`s slot3."
    ::= { slot3Entry 1 }

slot3Type OBJECT-TYPE
    SYNTAX      DisplayString (SIZE (0..255))
    MAX-ACCESS  read-only
    STATUS      current
    DESCRIPTION
            "the slot3Type of each chassis."
    ::= { slot3Entry 2 }

slot3Status OBJECT-TYPE
    SYNTAX      DisplayString (SIZE (0..255))
    MAX-ACCESS  read-only
    STATUS      current
    DESCRIPTION
            "A string to describe the board status." 
    ::= { slot3Entry 3 }   

slot3Id OBJECT-TYPE
    SYNTAX      Integer32
    MAX-ACCESS  read-only
    STATUS      current
    DESCRIPTION
            "slot id."
    ::= { slot3Entry 4 }

slot3Module OBJECT IDENTIFIER ::= { slot3 2 }

-- slot3ModuleTable --
slot3ModuleTable OBJECT-TYPE
    SYNTAX      SEQUENCE OF Slot3ModuleEntry
    MAX-ACCESS  not-accessible
    STATUS      current
    DESCRIPTION
            "A list of all slot3Module's utilization."
    ::= { slot3Module 1 }  

slot3ModuleEntry OBJECT-TYPE
    SYNTAX      Slot3ModuleEntry
    MAX-ACCESS  not-accessible
    STATUS      current
    DESCRIPTION
            "An entry contains a slot3Module's utilization."
    INDEX   { slot3ModuleIndex }
    ::= { slot3ModuleTable 1 }

Slot3ModuleEntry ::=
    SEQUENCE {     
		slot3ModuleIndex                       Integer32,
		slot3ModuleId                           DisplayString,  
		slot3ModuleIfNumber                     Integer32		
    } 

slot3ModuleIndex OBJECT-TYPE
    SYNTAX      Integer32 (1..2147483647)
    MAX-ACCESS  not-accessible
    STATUS      current
    DESCRIPTION
            "A unique value, greater than zero, for each chassis`s slot3."
    ::= { slot3ModuleEntry 1 }

slot3ModuleId OBJECT-TYPE
    SYNTAX      DisplayString (SIZE (0..32))
    MAX-ACCESS  read-only
    STATUS      current
    DESCRIPTION
            "the value of module`s id"
    ::= { slot3ModuleEntry 2 }
  
slot3ModuleIfNumber OBJECT-TYPE
    SYNTAX      Integer32(0..2147483647)
    MAX-ACCESS  read-only
    STATUS      current
    DESCRIPTION
            "The number of network interfaces (regardless of their
            current state) present on this system." 
    ::= { slot3ModuleEntry 3 } 
    
slot3ModuleIfTable OBJECT-TYPE
    SYNTAX      SEQUENCE OF Slot3ModuleIfEntry
    MAX-ACCESS  not-accessible
    STATUS      current
    DESCRIPTION
            "A list of interface entries.  The number of entries is
            given by the value of ifNumber."
    ::= { slot3Module 2 } 
    
slot3ModuleIfEntry OBJECT-TYPE
    SYNTAX      Slot3ModuleIfEntry
    MAX-ACCESS  not-accessible
    STATUS      current
    DESCRIPTION
            "An entry containing management information applicable to a
            particular interface."
    INDEX   { slot3ModuleifIndex }
    ::= { slot3ModuleIfTable 1 }
    
Slot3ModuleIfEntry ::=
    SEQUENCE {
        slot3ModuleifIndex                 InterfaceIndex,  
        slot3ModuleIfId                    DisplayString,  
        slot3ModuleifDescr                 DisplayString,           
        slot3ModuleifType                  IANAifType,   		
        slot3ModuleifMtu                   Integer32,                
        slot3ModuleifSpeed                 Counter64,               
        slot3ModuleifPhysAddress           PhysAddress,              
        slot3ModuleifAdminStatus           INTEGER,                  
        slot3ModuleifOperStatus            INTEGER,                  
        slot3ModuleifLastChange            TimeTicks,                
	slot3ModuleifInKbits   	           Counter64,
	slot3ModuleifOutKbits              Counter64,
        slot3ModuleifInOctets              Counter64,                
        slot3ModuleifInUcastPkts           Counter64,                
        slot3ModuleifInNUcastPkts          Counter64,    
        slot3ModuleifInDiscards            Counter64,
        slot3ModuleifInErrors              Counter64,
        slot3ModuleifInFcsErrorPkts        Counter64,
        slot3ModuleifInUnknownProtos       Counter64,	-- deprecated
        slot3ModuleifOutOctets             Counter64,
        slot3ModuleifOutUcastPkts          Counter64,
        slot3ModuleifOutNUcastPkts         Counter64,  -- deprecated
        slot3ModuleifOutDiscards           Counter64,
        slot3ModuleifOutErrors             Counter64,
        slot3ModuleifOutFcsErrorPkts       Counter64,
        slot3ModuleifOutQLen               Gauge32,    -- deprecated  
	    slot3ModuleifInpps   	           Counter64,
	    slot3ModuleifOutpps              Counter64,
        slot3ModuleifRxPower                DisplayString,
        slot3ModuleifTxPower                DisplayString,
        slot3ModuleifSpecific              OBJECT IDENTIFIER
    }         

slot3ModuleifIndex OBJECT-TYPE
    SYNTAX      InterfaceIndex
    MAX-ACCESS  read-only
    STATUS      current
    DESCRIPTION
            "A unique value, greater than zero, for each interface.  It
            is recommended that values are assigned contiguously
            starting from 1.  The value for each interface sub-layer
            must remain constant at least from one re-initialization of
            the entity's network management system to the next re-
            initialization."
    ::= { slot3ModuleIfEntry 1 }
    
slot3ModuleIfId OBJECT-TYPE
    SYNTAX      DisplayString (SIZE (0..32))
    MAX-ACCESS  read-only
    STATUS      current
    DESCRIPTION
            "the value of module`s id"
    ::= { slot3ModuleIfEntry 2 }
    
slot3ModuleifDescr OBJECT-TYPE
    SYNTAX      DisplayString (SIZE (0..255))
    MAX-ACCESS  read-only
    STATUS      current
    DESCRIPTION
            "A textual string containing information about the
            interface.  This string should include the name of the
            manufacturer, the product name and the version of the
            interface hardware/software."
    ::= { slot3ModuleIfEntry 3 }
    
slot3ModuleifType OBJECT-TYPE
    SYNTAX      IANAifType
    MAX-ACCESS  read-only
    STATUS      current
    DESCRIPTION
            "The type of interface.  Additional values for ifType are
            assigned by the Internet Assigned Numbers Authority (IANA),
            through updating the syntax of the IANAifType textual
            convention."
    ::= { slot3ModuleIfEntry 4 }

slot3ModuleifMtu OBJECT-TYPE
    SYNTAX      Integer32(1..2147483647)
    MAX-ACCESS  read-only
    STATUS      current
    DESCRIPTION
            "The size of the largest packet which can be sent/received
            on the interface, specified in octets.  For interfaces that
            are used for transmitting network datagrams, this is the
            size of the largest network datagram that can be sent on the
            interface."
    ::= { slot3ModuleIfEntry 5 }

slot3ModuleifSpeed OBJECT-TYPE
    SYNTAX      Counter64
    MAX-ACCESS  read-only
    STATUS      current
    DESCRIPTION
            "An estimate of the interface's current bandwidth in bits
            per second.  For interfaces which do not vary in bandwidth
            or for those where no accurate estimation can be made, this
            object should contain the nominal bandwidth. For a sub-layer
            which has no concept of bandwidth, this object should be zero."
    ::= { slot3ModuleIfEntry 6 }

slot3ModuleifPhysAddress OBJECT-TYPE
    SYNTAX      PhysAddress
    MAX-ACCESS  read-only
    STATUS      current
    DESCRIPTION
            "The interface's address at its protocol sub-layer.  For
            example, for an 802.x interface, this object normally
            contains a MAC address.  The interface's media-specific MIB
            must define the bit and byte ordering and the format of the
            value of this object.  For interfaces which do not have such
            an address (e.g., a serial line), this object should contain
            an octet string of zero length."
    ::= { slot3ModuleIfEntry 7 }
    
slot3ModuleifAdminStatus OBJECT-TYPE
    SYNTAX  INTEGER {
                up(1),       -- ready to pass packets
                down(2),
                testing(3)   -- in some test mode
            }
    MAX-ACCESS  read-write
    STATUS      current
    DESCRIPTION
            "The desired state of the interface.  The testing(3) state
            indicates that no operational packets can be passed.  When a
            managed system initializes, all interfaces start with
            ifAdminStatus in the down(2) state.  As a result of either
            explicit management action or per configuration information
            retained by the managed system, ifAdminStatus is then
            changed to either the up(1) or testing(3) states (or remains
            in the down(2) state)."
    ::= { slot3ModuleIfEntry 8 }

slot3ModuleifOperStatus OBJECT-TYPE
    SYNTAX  INTEGER {
                up(1),        -- ready to pass packets
                down(2),
                testing(3),   -- in some test mode
                unknown(4),   -- status can not be determined
                              -- for some reason.
                dormant(5),
                notPresent(6),    -- some component is missing
                lowerLayerDown(7) -- down due to state of
                                  -- lower-layer interface(s)
            }
    MAX-ACCESS  read-only
    STATUS      current
    DESCRIPTION
            "The current operational state of the interface.  The
            testing(3) state indicates that no operational packets can
            be passed.  If ifAdminStatus is down(2) then ifOperStatus
            should be down(2).  If ifAdminStatus is changed to up(1)
            then ifOperStatus should change to up(1) if the interface is
            ready to transmit and receive network traffic; it should
            change to dormant(5) if the interface is waiting for
            external actions (such as a serial line waiting for an
            incoming connection); it should remain in the down(2) state
            if and only if there is a fault that prevents it from going
            to the up(1) state; it should remain in the notPresent(6)
            state if the interface has missing (typically, hardware)
            components."
    ::= { slot3ModuleIfEntry 9 }

slot3ModuleifLastChange OBJECT-TYPE
    SYNTAX      TimeTicks
    MAX-ACCESS  read-only
    STATUS      current
    DESCRIPTION
            "The value of sysUpTime at the time the interface entered
            its current operational state.  If the current state was
            entered prior to the last re-initialization of the local
            network management subsystem, then this object contains a
            zero value."
    ::= { slot3ModuleIfEntry 10 }

slot3ModuleifInKbits OBJECT-TYPE
    SYNTAX      Counter64
    MAX-ACCESS  read-only
    STATUS      current
    DESCRIPTION
            "The real time rate received on the interface, in Kbits
	    format.

            Discontinuities in the value of this counter can occur at
            re-initialization of the management system, and at other
            times as indicated by the value of
            ifCounterDiscontinuityTime."
    ::= { slot3ModuleIfEntry 11 }

slot3ModuleifOutKbits OBJECT-TYPE
    SYNTAX      Counter64
    MAX-ACCESS  read-only
    STATUS      current
    DESCRIPTION
            "The real time rate send on the interface, in Kbits
	    format.

            Discontinuities in the value of this counter can occur at
            re-initialization of the management system, and at other
            times as indicated by the value of
            ifCounterDiscontinuityTime."
    ::= { slot3ModuleIfEntry 12 }

slot3ModuleifInOctets OBJECT-TYPE
    SYNTAX      Counter64
    MAX-ACCESS  read-only
    STATUS      current
    DESCRIPTION
            "The total number of octets received on the interface,
            including framing characters.

            Discontinuities in the value of this counter can occur at
            re-initialization of the management system, and at other
            times as indicated by the value of
            ifCounterDiscontinuityTime."
    ::= { slot3ModuleIfEntry 13 }

slot3ModuleifInUcastPkts OBJECT-TYPE
    SYNTAX      Counter64
    MAX-ACCESS  read-only
    STATUS      current
    DESCRIPTION
            "The number of packets, delivered by this sub-layer to a
            higher (sub-)layer, which were not addressed to a multicast
            or broadcast address at this sub-layer.

            Discontinuities in the value of this counter can occur at
            re-initialization of the management system, and at other
            times as indicated by the value of
            ifCounterDiscontinuityTime."
    ::= { slot3ModuleIfEntry 14 }

slot3ModuleifInNUcastPkts OBJECT-TYPE
    SYNTAX  Counter64
    MAX-ACCESS  read-only
    STATUS      current
    DESCRIPTION
            "The number of packets, delivered by this sub-layer to a
            higher (sub-)layer, which were addressed to a multicast or
            broadcast address at this sub-layer.

            Discontinuities in the value of this counter can occur at
            re-initialization of the management system, and at other
            times as indicated by the value of
            ifCounterDiscontinuityTime.

            This object is deprecated in favour of ifInMulticastPkts and
            ifInBroadcastPkts."
    ::= { slot3ModuleIfEntry 15 }

slot3ModuleifInDiscards OBJECT-TYPE
    SYNTAX      Counter64
    MAX-ACCESS  read-only
    STATUS      current
    DESCRIPTION
            "The number of inbound packets which were chosen to be
            discarded even though no errors had been detected to prevent

            their being deliverable to a higher-layer protocol.  One
            possible reason for discarding such a packet could be to
            free up buffer space.

            Discontinuities in the value of this counter can occur at
            re-initialization of the management system, and at other
            times as indicated by the value of
            ifCounterDiscontinuityTime."
    ::= { slot3ModuleIfEntry 16 }

slot3ModuleifInErrors OBJECT-TYPE
    SYNTAX      Counter64
    MAX-ACCESS  read-only
    STATUS      current
    DESCRIPTION
            "For packet-oriented interfaces, the number of inbound
            packets that contained errors preventing them from being
            deliverable to a higher-layer protocol.  For character-
            oriented or fixed-length interfaces, the number of inbound
            transmission units that contained errors preventing them
            from being deliverable to a higher-layer protocol.

            Discontinuities in the value of this counter can occur at
            re-initialization of the management system, and at other
            times as indicated by the value of
            ifCounterDiscontinuityTime."
    ::= { slot3ModuleIfEntry 17 }

slot3ModuleifInFcsErrorPkts OBJECT-TYPE
    SYNTAX      Counter64
    MAX-ACCESS  read-only
    STATUS      current
    DESCRIPTION
            "FCS error pakets."
    ::= { slot3ModuleIfEntry 18 }

slot3ModuleifInUnknownProtos OBJECT-TYPE
    SYNTAX      Counter64
    MAX-ACCESS  read-only
    STATUS      current
    DESCRIPTION
            "For packet-oriented interfaces, the number of packets
            received via the interface which were discarded because of
            an unknown or unsupported protocol.  For character-oriented
            or fixed-length interfaces that support protocol
            multiplexing the number of transmission units received via
            the interface which were discarded because of an unknown or
            unsupported protocol.  For any interface that does not
            support protocol multiplexing, this counter will always be
            0.

            Discontinuities in the value of this counter can occur at
            re-initialization of the management system, and at other
            times as indicated by the value of
            ifCounterDiscontinuityTime."
    ::= { slot3ModuleIfEntry 19 }

slot3ModuleifOutOctets OBJECT-TYPE
    SYNTAX      Counter64
    MAX-ACCESS  read-only
    STATUS      current
    DESCRIPTION
            "The total number of octets transmitted out of the
            interface, including framing characters.

            Discontinuities in the value of this counter can occur at
            re-initialization of the management system, and at other
            times as indicated by the value of
            ifCounterDiscontinuityTime."
    ::= { slot3ModuleIfEntry 20 }

slot3ModuleifOutUcastPkts OBJECT-TYPE
    SYNTAX      Counter64
    MAX-ACCESS  read-only
    STATUS      current
    DESCRIPTION
            "The total number of packets that higher-level protocols
            requested be transmitted, and which were not addressed to a
            multicast or broadcast address at this sub-layer, including
            those that were discarded or not sent.

            Discontinuities in the value of this counter can occur at
            re-initialization of the management system, and at other
            times as indicated by the value of
            ifCounterDiscontinuityTime."
    ::= { slot3ModuleIfEntry 21 }

slot3ModuleifOutNUcastPkts OBJECT-TYPE
    SYNTAX      Counter64
    MAX-ACCESS  read-only
    STATUS      deprecated
    DESCRIPTION
            "The total number of packets that higher-level protocols
            requested be transmitted, and which were addressed to a
            multicast or broadcast address at this sub-layer, including
            those that were discarded or not sent.

            Discontinuities in the value of this counter can occur at
            re-initialization of the management system, and at other
            times as indicated by the value of
            ifCounterDiscontinuityTime.

            This object is deprecated in favour of ifOutMulticastPkts
            and ifOutBroadcastPkts."
    ::= { slot3ModuleIfEntry 22 }

slot3ModuleifOutDiscards OBJECT-TYPE
    SYNTAX      Counter64
    MAX-ACCESS  read-only
    STATUS      current
    DESCRIPTION
            "The number of outbound packets which were chosen to be
            discarded even though no errors had been detected to prevent
            their being transmitted.  One possible reason for discarding
            such a packet could be to free up buffer space.

            Discontinuities in the value of this counter can occur at
            re-initialization of the management system, and at other
            times as indicated by the value of
            ifCounterDiscontinuityTime."
    ::= { slot3ModuleIfEntry 23 }

slot3ModuleifOutErrors OBJECT-TYPE
    SYNTAX      Counter64
    MAX-ACCESS  read-only
    STATUS      current
    DESCRIPTION
            "For packet-oriented interfaces, the number of outbound
            packets that could not be transmitted because of errors.
            For character-oriented or fixed-length interfaces, the
            number of outbound transmission units that could not be
            transmitted because of errors.

            Discontinuities in the value of this counter can occur at
            re-initialization of the management system, and at other
            times as indicated by the value of
            ifCounterDiscontinuityTime."
    ::= { slot3ModuleIfEntry 24 }

slot3ModuleifOutFcsErrorPkts OBJECT-TYPE
    SYNTAX      Counter64
    MAX-ACCESS  read-only
    STATUS      current
    DESCRIPTION
            "FCS error pakets."
    ::= { slot3ModuleIfEntry 25 }

slot3ModuleifOutQLen OBJECT-TYPE
    SYNTAX      Gauge32
    MAX-ACCESS  read-only
    STATUS      deprecated
    DESCRIPTION
            "The length of the output packet queue (in packets)."
    ::= { slot3ModuleIfEntry 26 }

slot3ModuleifInpps OBJECT-TYPE
    SYNTAX      Counter64
    MAX-ACCESS  read-only
    STATUS      current
    DESCRIPTION
            "The real time rate received on the interface, in pps
	    format.

            Discontinuities in the value of this counter can occur at
            re-initialization of the management system, and at other
            times as indicated by the value of
            ifCounterDiscontinuityTime."
    ::= { slot3ModuleIfEntry 27 }

slot3ModuleifOutpps OBJECT-TYPE
    SYNTAX      Counter64
    MAX-ACCESS  read-only
    STATUS      current
    DESCRIPTION
            "The real time rate send on the interface, in pps
	    format.

            Discontinuities in the value of this counter can occur at
            re-initialization of the management system, and at other
            times as indicated by the value of
            ifCounterDiscontinuityTime."
    ::= { slot3ModuleIfEntry 28 }
    
slot3ModuleifRxPower OBJECT-TYPE
    SYNTAX      DisplayString (SIZE (0..255))
    MAX-ACCESS  read-only
    STATUS      current
    DESCRIPTION
            "the value of interface's received power, in dbm format."
    ::= { slot3ModuleIfEntry 29 }
    
slot3ModuleifTxPower OBJECT-TYPE
    SYNTAX      DisplayString (SIZE (0..255))
    MAX-ACCESS  read-only
    STATUS      current
    DESCRIPTION
            "the value of interface's send power, in dbm format."
    ::= { slot3ModuleIfEntry 30 }

slot3ModuleifSpecific OBJECT-TYPE
    SYNTAX      OBJECT IDENTIFIER
    MAX-ACCESS  read-only
    STATUS      deprecated
    DESCRIPTION
            "A reference to MIB definitions specific to the particular
            media being used to realize the interface.  It is

            recommended that this value point to an instance of a MIB
            object in the media-specific MIB, i.e., that this object
            have the semantics associated with the InstancePointer
            textual convention defined in RFC 2579.  In fact, it is
            recommended that the media-specific MIB specify what value
            ifSpecific should/can take for values of ifType.  If no MIB
            definitions specific to the particular media are available,
            the value should be set to the OBJECT IDENTIFIER { 0 0 }."
    ::= { slot3ModuleIfEntry 31 }  

-- slot 4 --

-- slot4Table --

slot4Table OBJECT-TYPE
    SYNTAX      SEQUENCE OF Slot4Entry
    MAX-ACCESS  not-accessible
    STATUS      current
    DESCRIPTION
            "A list of all slot4Type's utilization."
    ::= { slot4 1 }  

slot4Entry OBJECT-TYPE
    SYNTAX      Slot4Entry
    MAX-ACCESS  not-accessible
    STATUS      current
    DESCRIPTION
            "An entry contains a slot4's utilization."
    INDEX   { slot4Index }
    ::= { slot4Table 1 }

Slot4Entry ::=
    SEQUENCE {     
		slot4Index                       Integer32,
		slot4Type                        DisplayString,
		slot4Status                      DisplayString,		
		slot4Id                          Integer32
    }  

slot4Index OBJECT-TYPE
    SYNTAX      Integer32 (1..2147483647)
    MAX-ACCESS  not-accessible
    STATUS      current
    DESCRIPTION
            "A unique value, greater than zero, for each chassis`s slot4."
    ::= { slot4Entry 1 }

slot4Type OBJECT-TYPE
    SYNTAX      DisplayString (SIZE (0..255))
    MAX-ACCESS  read-only
    STATUS      current
    DESCRIPTION
            "the slot4Type of each chassis."
    ::= { slot4Entry 2 }

slot4Status OBJECT-TYPE
    SYNTAX      DisplayString (SIZE (0..255))
    MAX-ACCESS  read-only
    STATUS      current
    DESCRIPTION
            "A string to describe the board status." 
    ::= { slot4Entry 3 }   

slot4Id OBJECT-TYPE
    SYNTAX      Integer32
    MAX-ACCESS  read-only
    STATUS      current
    DESCRIPTION
            "slot id."
    ::= { slot4Entry 4 }

slot4Module OBJECT IDENTIFIER ::= { slot4 2 }

-- slot4ModuleTable --
slot4ModuleTable OBJECT-TYPE
    SYNTAX      SEQUENCE OF Slot4ModuleEntry
    MAX-ACCESS  not-accessible
    STATUS      current
    DESCRIPTION
            "A list of all slot4Module's utilization."
    ::= { slot4Module 1 }  

slot4ModuleEntry OBJECT-TYPE
    SYNTAX      Slot4ModuleEntry
    MAX-ACCESS  not-accessible
    STATUS      current
    DESCRIPTION
            "An entry contains a slot4Module's utilization."
    INDEX   { slot4ModuleIndex }
    ::= { slot4ModuleTable 1 }

Slot4ModuleEntry ::=
    SEQUENCE {     
		slot4ModuleIndex                       Integer32,
		slot4ModuleId                           DisplayString,  
		slot4ModuleIfNumber                     Integer32		
    } 

slot4ModuleIndex OBJECT-TYPE
    SYNTAX      Integer32 (1..2147483647)
    MAX-ACCESS  not-accessible
    STATUS      current
    DESCRIPTION
            "A unique value, greater than zero, for each chassis`s slot4."
    ::= { slot4ModuleEntry 1 }

slot4ModuleId OBJECT-TYPE
    SYNTAX      DisplayString (SIZE (0..32))
    MAX-ACCESS  read-only
    STATUS      current
    DESCRIPTION
            "the value of module`s id"
    ::= { slot4ModuleEntry 2 }
  
slot4ModuleIfNumber OBJECT-TYPE
    SYNTAX      Integer32(0..2147483647)
    MAX-ACCESS  read-only
    STATUS      current
    DESCRIPTION
            "The number of network interfaces (regardless of their
            current state) present on this system." 
    ::= { slot4ModuleEntry 3 } 
    
slot4ModuleIfTable OBJECT-TYPE
    SYNTAX      SEQUENCE OF Slot4ModuleIfEntry
    MAX-ACCESS  not-accessible
    STATUS      current
    DESCRIPTION
            "A list of interface entries.  The number of entries is
            given by the value of ifNumber."
    ::= { slot4Module 2 } 
    
slot4ModuleIfEntry OBJECT-TYPE
    SYNTAX      Slot4ModuleIfEntry
    MAX-ACCESS  not-accessible
    STATUS      current
    DESCRIPTION
            "An entry containing management information applicable to a
            particular interface."
    INDEX   { slot4ModuleifIndex }
    ::= { slot4ModuleIfTable 1 }
    
Slot4ModuleIfEntry ::=
    SEQUENCE {
        slot4ModuleifIndex                 InterfaceIndex,  
        slot4ModuleIfId                    DisplayString,  
        slot4ModuleifDescr                 DisplayString,           
        slot4ModuleifType                  IANAifType,   		
        slot4ModuleifMtu                   Integer32,                
        slot4ModuleifSpeed                 Counter64,               
        slot4ModuleifPhysAddress           PhysAddress,              
        slot4ModuleifAdminStatus           INTEGER,                  
        slot4ModuleifOperStatus            INTEGER,                  
        slot4ModuleifLastChange            TimeTicks,                
	slot4ModuleifInKbits   	           Counter64,
	slot4ModuleifOutKbits              Counter64,
        slot4ModuleifInOctets              Counter64,                
        slot4ModuleifInUcastPkts           Counter64,                
        slot4ModuleifInNUcastPkts          Counter64,    
        slot4ModuleifInDiscards            Counter64,
        slot4ModuleifInErrors              Counter64,
        slot4ModuleifInFcsErrorPkts        Counter64,
        slot4ModuleifInUnknownProtos       Counter64,	-- deprecated
        slot4ModuleifOutOctets             Counter64,
        slot4ModuleifOutUcastPkts          Counter64,
        slot4ModuleifOutNUcastPkts         Counter64,  -- deprecated
        slot4ModuleifOutDiscards           Counter64,
        slot4ModuleifOutErrors             Counter64,
        slot4ModuleifOutFcsErrorPkts       Counter64,
        slot4ModuleifOutQLen               Gauge32,    -- deprecated  
	    slot4ModuleifInpps   	           Counter64,
    	slot4ModuleifOutpps              Counter64,        
        slot4ModuleifRxPower                DisplayString,
        slot4ModuleifTxPower                DisplayString,
        slot4ModuleifSpecific              OBJECT IDENTIFIER
    }         

slot4ModuleifIndex OBJECT-TYPE
    SYNTAX      InterfaceIndex
    MAX-ACCESS  read-only
    STATUS      current
    DESCRIPTION
            "A unique value, greater than zero, for each interface.  It
            is recommended that values are assigned contiguously
            starting from 1.  The value for each interface sub-layer
            must remain constant at least from one re-initialization of
            the entity's network management system to the next re-
            initialization."
    ::= { slot4ModuleIfEntry 1 }
    
slot4ModuleIfId OBJECT-TYPE
    SYNTAX      DisplayString (SIZE (0..32))
    MAX-ACCESS  read-only
    STATUS      current
    DESCRIPTION
            "the value of module`s id"
    ::= { slot4ModuleIfEntry 2 }
    
slot4ModuleifDescr OBJECT-TYPE
    SYNTAX      DisplayString (SIZE (0..255))
    MAX-ACCESS  read-only
    STATUS      current
    DESCRIPTION
            "A textual string containing information about the
            interface.  This string should include the name of the
            manufacturer, the product name and the version of the
            interface hardware/software."
    ::= { slot4ModuleIfEntry 3 }
    
slot4ModuleifType OBJECT-TYPE
    SYNTAX      IANAifType
    MAX-ACCESS  read-only
    STATUS      current
    DESCRIPTION
            "The type of interface.  Additional values for ifType are
            assigned by the Internet Assigned Numbers Authority (IANA),
            through updating the syntax of the IANAifType textual
            convention."
    ::= { slot4ModuleIfEntry 4 }

slot4ModuleifMtu OBJECT-TYPE
    SYNTAX      Integer32(1..2147483647)
    MAX-ACCESS  read-only
    STATUS      current
    DESCRIPTION
            "The size of the largest packet which can be sent/received
            on the interface, specified in octets.  For interfaces that
            are used for transmitting network datagrams, this is the
            size of the largest network datagram that can be sent on the
            interface."
    ::= { slot4ModuleIfEntry 5 }

slot4ModuleifSpeed OBJECT-TYPE
    SYNTAX      Counter64
    MAX-ACCESS  read-only
    STATUS      current
    DESCRIPTION
            "An estimate of the interface's current bandwidth in bits
            per second.  For interfaces which do not vary in bandwidth
            or for those where no accurate estimation can be made, this
            object should contain the nominal bandwidth. For a sub-layer
            which has no concept of bandwidth, this object should be zero."
    ::= { slot4ModuleIfEntry 6 }

slot4ModuleifPhysAddress OBJECT-TYPE
    SYNTAX      PhysAddress
    MAX-ACCESS  read-only
    STATUS      current
    DESCRIPTION
            "The interface's address at its protocol sub-layer.  For
            example, for an 802.x interface, this object normally
            contains a MAC address.  The interface's media-specific MIB
            must define the bit and byte ordering and the format of the
            value of this object.  For interfaces which do not have such
            an address (e.g., a serial line), this object should contain
            an octet string of zero length."
    ::= { slot4ModuleIfEntry 7 }
    
slot4ModuleifAdminStatus OBJECT-TYPE
    SYNTAX  INTEGER {
                up(1),       -- ready to pass packets
                down(2),
                testing(3)   -- in some test mode
            }
    MAX-ACCESS  read-write
    STATUS      current
    DESCRIPTION
            "The desired state of the interface.  The testing(3) state
            indicates that no operational packets can be passed.  When a
            managed system initializes, all interfaces start with
            ifAdminStatus in the down(2) state.  As a result of either
            explicit management action or per configuration information
            retained by the managed system, ifAdminStatus is then
            changed to either the up(1) or testing(3) states (or remains
            in the down(2) state)."
    ::= { slot4ModuleIfEntry 8 }

slot4ModuleifOperStatus OBJECT-TYPE
    SYNTAX  INTEGER {
                up(1),        -- ready to pass packets
                down(2),
                testing(3),   -- in some test mode
                unknown(4),   -- status can not be determined
                              -- for some reason.
                dormant(5),
                notPresent(6),    -- some component is missing
                lowerLayerDown(7) -- down due to state of
                                  -- lower-layer interface(s)
            }
    MAX-ACCESS  read-only
    STATUS      current
    DESCRIPTION
            "The current operational state of the interface.  The
            testing(3) state indicates that no operational packets can
            be passed.  If ifAdminStatus is down(2) then ifOperStatus
            should be down(2).  If ifAdminStatus is changed to up(1)
            then ifOperStatus should change to up(1) if the interface is
            ready to transmit and receive network traffic; it should
            change to dormant(5) if the interface is waiting for
            external actions (such as a serial line waiting for an
            incoming connection); it should remain in the down(2) state
            if and only if there is a fault that prevents it from going
            to the up(1) state; it should remain in the notPresent(6)
            state if the interface has missing (typically, hardware)
            components."
    ::= { slot4ModuleIfEntry 9 }

slot4ModuleifLastChange OBJECT-TYPE
    SYNTAX      TimeTicks
    MAX-ACCESS  read-only
    STATUS      current
    DESCRIPTION
            "The value of sysUpTime at the time the interface entered
            its current operational state.  If the current state was
            entered prior to the last re-initialization of the local
            network management subsystem, then this object contains a
            zero value."
    ::= { slot4ModuleIfEntry 10 }

slot4ModuleifInKbits OBJECT-TYPE
    SYNTAX      Counter64
    MAX-ACCESS  read-only
    STATUS      current
    DESCRIPTION
            "The real time rate received on the interface, in Kbits
	    format.

            Discontinuities in the value of this counter can occur at
            re-initialization of the management system, and at other
            times as indicated by the value of
            ifCounterDiscontinuityTime."
    ::= { slot4ModuleIfEntry 11 }

slot4ModuleifOutKbits OBJECT-TYPE
    SYNTAX      Counter64
    MAX-ACCESS  read-only
    STATUS      current
    DESCRIPTION
            "The real time rate send on the interface, in Kbits
	    format.

            Discontinuities in the value of this counter can occur at
            re-initialization of the management system, and at other
            times as indicated by the value of
            ifCounterDiscontinuityTime."
    ::= { slot4ModuleIfEntry 12 }

slot4ModuleifInOctets OBJECT-TYPE
    SYNTAX      Counter64
    MAX-ACCESS  read-only
    STATUS      current
    DESCRIPTION
            "The total number of octets received on the interface,
            including framing characters.

            Discontinuities in the value of this counter can occur at
            re-initialization of the management system, and at other
            times as indicated by the value of
            ifCounterDiscontinuityTime."
    ::= { slot4ModuleIfEntry 13 }

slot4ModuleifInUcastPkts OBJECT-TYPE
    SYNTAX      Counter64
    MAX-ACCESS  read-only
    STATUS      current
    DESCRIPTION
            "The number of packets, delivered by this sub-layer to a
            higher (sub-)layer, which were not addressed to a multicast
            or broadcast address at this sub-layer.

            Discontinuities in the value of this counter can occur at
            re-initialization of the management system, and at other
            times as indicated by the value of
            ifCounterDiscontinuityTime."
    ::= { slot4ModuleIfEntry 14 }

slot4ModuleifInNUcastPkts OBJECT-TYPE
    SYNTAX  Counter64
    MAX-ACCESS  read-only
    STATUS      current
    DESCRIPTION
            "The number of packets, delivered by this sub-layer to a
            higher (sub-)layer, which were addressed to a multicast or
            broadcast address at this sub-layer.

            Discontinuities in the value of this counter can occur at
            re-initialization of the management system, and at other
            times as indicated by the value of
            ifCounterDiscontinuityTime.

            This object is deprecated in favour of ifInMulticastPkts and
            ifInBroadcastPkts."
    ::= { slot4ModuleIfEntry 15 }

slot4ModuleifInDiscards OBJECT-TYPE
    SYNTAX      Counter64
    MAX-ACCESS  read-only
    STATUS      current
    DESCRIPTION
            "The number of inbound packets which were chosen to be
            discarded even though no errors had been detected to prevent

            their being deliverable to a higher-layer protocol.  One
            possible reason for discarding such a packet could be to
            free up buffer space.

            Discontinuities in the value of this counter can occur at
            re-initialization of the management system, and at other
            times as indicated by the value of
            ifCounterDiscontinuityTime."
    ::= { slot4ModuleIfEntry 16 }

slot4ModuleifInErrors OBJECT-TYPE
    SYNTAX      Counter64
    MAX-ACCESS  read-only
    STATUS      current
    DESCRIPTION
            "For packet-oriented interfaces, the number of inbound
            packets that contained errors preventing them from being
            deliverable to a higher-layer protocol.  For character-
            oriented or fixed-length interfaces, the number of inbound
            transmission units that contained errors preventing them
            from being deliverable to a higher-layer protocol.

            Discontinuities in the value of this counter can occur at
            re-initialization of the management system, and at other
            times as indicated by the value of
            ifCounterDiscontinuityTime."
    ::= { slot4ModuleIfEntry 17 }

slot4ModuleifInFcsErrorPkts OBJECT-TYPE
    SYNTAX      Counter64
    MAX-ACCESS  read-only
    STATUS      current
    DESCRIPTION
            "FCS error pakets."
    ::= { slot4ModuleIfEntry 18 }

slot4ModuleifInUnknownProtos OBJECT-TYPE
    SYNTAX      Counter64
    MAX-ACCESS  read-only
    STATUS      current
    DESCRIPTION
            "For packet-oriented interfaces, the number of packets
            received via the interface which were discarded because of
            an unknown or unsupported protocol.  For character-oriented
            or fixed-length interfaces that support protocol
            multiplexing the number of transmission units received via
            the interface which were discarded because of an unknown or
            unsupported protocol.  For any interface that does not
            support protocol multiplexing, this counter will always be
            0.

            Discontinuities in the value of this counter can occur at
            re-initialization of the management system, and at other
            times as indicated by the value of
            ifCounterDiscontinuityTime."
    ::= { slot4ModuleIfEntry 19 }

slot4ModuleifOutOctets OBJECT-TYPE
    SYNTAX      Counter64
    MAX-ACCESS  read-only
    STATUS      current
    DESCRIPTION
            "The total number of octets transmitted out of the
            interface, including framing characters.

            Discontinuities in the value of this counter can occur at
            re-initialization of the management system, and at other
            times as indicated by the value of
            ifCounterDiscontinuityTime."
    ::= { slot4ModuleIfEntry 20 }

slot4ModuleifOutUcastPkts OBJECT-TYPE
    SYNTAX      Counter64
    MAX-ACCESS  read-only
    STATUS      current
    DESCRIPTION
            "The total number of packets that higher-level protocols
            requested be transmitted, and which were not addressed to a
            multicast or broadcast address at this sub-layer, including
            those that were discarded or not sent.

            Discontinuities in the value of this counter can occur at
            re-initialization of the management system, and at other
            times as indicated by the value of
            ifCounterDiscontinuityTime."
    ::= { slot4ModuleIfEntry 21 }

slot4ModuleifOutNUcastPkts OBJECT-TYPE
    SYNTAX      Counter64
    MAX-ACCESS  read-only
    STATUS      deprecated
    DESCRIPTION
            "The total number of packets that higher-level protocols
            requested be transmitted, and which were addressed to a
            multicast or broadcast address at this sub-layer, including
            those that were discarded or not sent.

            Discontinuities in the value of this counter can occur at
            re-initialization of the management system, and at other
            times as indicated by the value of
            ifCounterDiscontinuityTime.

            This object is deprecated in favour of ifOutMulticastPkts
            and ifOutBroadcastPkts."
    ::= { slot4ModuleIfEntry 22 }

slot4ModuleifOutDiscards OBJECT-TYPE
    SYNTAX      Counter64
    MAX-ACCESS  read-only
    STATUS      current
    DESCRIPTION
            "The number of outbound packets which were chosen to be
            discarded even though no errors had been detected to prevent
            their being transmitted.  One possible reason for discarding
            such a packet could be to free up buffer space.

            Discontinuities in the value of this counter can occur at
            re-initialization of the management system, and at other
            times as indicated by the value of
            ifCounterDiscontinuityTime."
    ::= { slot4ModuleIfEntry 23 }

slot4ModuleifOutErrors OBJECT-TYPE
    SYNTAX      Counter64
    MAX-ACCESS  read-only
    STATUS      current
    DESCRIPTION
            "For packet-oriented interfaces, the number of outbound
            packets that could not be transmitted because of errors.
            For character-oriented or fixed-length interfaces, the
            number of outbound transmission units that could not be
            transmitted because of errors.

            Discontinuities in the value of this counter can occur at
            re-initialization of the management system, and at other
            times as indicated by the value of
            ifCounterDiscontinuityTime."
    ::= { slot4ModuleIfEntry 24 }

slot4ModuleifOutFcsErrorPkts OBJECT-TYPE
    SYNTAX      Counter64
    MAX-ACCESS  read-only
    STATUS      current
    DESCRIPTION
            "FCS error pakets."
    ::= { slot4ModuleIfEntry 25 }

slot4ModuleifOutQLen OBJECT-TYPE
    SYNTAX      Gauge32
    MAX-ACCESS  read-only
    STATUS      deprecated
    DESCRIPTION
            "The length of the output packet queue (in packets)."
    ::= { slot4ModuleIfEntry 26 }

slot4ModuleifInpps OBJECT-TYPE
    SYNTAX      Counter64
    MAX-ACCESS  read-only
    STATUS      current
    DESCRIPTION
            "The real time rate received on the interface, in pps
	    format.

            Discontinuities in the value of this counter can occur at
            re-initialization of the management system, and at other
            times as indicated by the value of
            ifCounterDiscontinuityTime."
    ::= { slot4ModuleIfEntry 27 }

slot4ModuleifOutpps OBJECT-TYPE
    SYNTAX      Counter64
    MAX-ACCESS  read-only
    STATUS      current
    DESCRIPTION
            "The real time rate send on the interface, in pps
	    format.

            Discontinuities in the value of this counter can occur at
            re-initialization of the management system, and at other
            times as indicated by the value of
            ifCounterDiscontinuityTime."
    ::= { slot4ModuleIfEntry 28 }

slot4ModuleifRxPower OBJECT-TYPE
    SYNTAX      DisplayString (SIZE (0..255))
    MAX-ACCESS  read-only
    STATUS      current
    DESCRIPTION
            "the value of interface's received power, in dbm format."
    ::= { slot4ModuleIfEntry 29 }
    
slot4ModuleifTxPower OBJECT-TYPE
    SYNTAX      DisplayString (SIZE (0..255))
    MAX-ACCESS  read-only
    STATUS      current
    DESCRIPTION
            "the value of interface's send power, in dbm format."
    ::= { slot4ModuleIfEntry 30 }

slot4ModuleifSpecific OBJECT-TYPE
    SYNTAX      OBJECT IDENTIFIER
    MAX-ACCESS  read-only
    STATUS      deprecated
    DESCRIPTION
            "A reference to MIB definitions specific to the particular
            media being used to realize the interface.  It is

            recommended that this value point to an instance of a MIB
            object in the media-specific MIB, i.e., that this object
            have the semantics associated with the InstancePointer
            textual convention defined in RFC 2579.  In fact, it is
            recommended that the media-specific MIB specify what value
            ifSpecific should/can take for values of ifType.  If no MIB
            definitions specific to the particular media are available,
            the value should be set to the OBJECT IDENTIFIER { 0 0 }."
    ::= { slot4ModuleIfEntry 31 }  

-- slot 5 --

-- slot5Table --

slot5Table OBJECT-TYPE
    SYNTAX      SEQUENCE OF Slot5Entry
    MAX-ACCESS  not-accessible
    STATUS      current
    DESCRIPTION
            "A list of all slot5Type's utilization."
    ::= { slot5 1 }  

slot5Entry OBJECT-TYPE
    SYNTAX      Slot5Entry
    MAX-ACCESS  not-accessible
    STATUS      current
    DESCRIPTION
            "An entry contains a slot5's utilization."
    INDEX   { slot5Index }
    ::= { slot5Table 1 }

Slot5Entry ::=
    SEQUENCE {     
		slot5Index                       Integer32,
		slot5Type                        DisplayString,
		slot5Status                      DisplayString,		
		slot5Id                          Integer32
    }  

slot5Index OBJECT-TYPE
    SYNTAX      Integer32 (1..2147483647)
    MAX-ACCESS  not-accessible
    STATUS      current
    DESCRIPTION
            "A unique value, greater than zero, for each chassis`s slot5."
    ::= { slot5Entry 1 }

slot5Type OBJECT-TYPE
    SYNTAX      DisplayString (SIZE (0..255))
    MAX-ACCESS  read-only
    STATUS      current
    DESCRIPTION
            "the slot5Type of each chassis."
    ::= { slot5Entry 2 }

slot5Status OBJECT-TYPE
    SYNTAX      DisplayString (SIZE (0..255))
    MAX-ACCESS  read-only
    STATUS      current
    DESCRIPTION
            "A string to describe the board status." 
    ::= { slot5Entry 3 }   

slot5Id OBJECT-TYPE
    SYNTAX      Integer32
    MAX-ACCESS  read-only
    STATUS      current
    DESCRIPTION
            "slot id."
    ::= { slot5Entry 4 }

slot5Module OBJECT IDENTIFIER ::= { slot5 2 }

-- slot5ModuleTable --
slot5ModuleTable OBJECT-TYPE
    SYNTAX      SEQUENCE OF Slot5ModuleEntry
    MAX-ACCESS  not-accessible
    STATUS      current
    DESCRIPTION
            "A list of all slot5Module's utilization."
    ::= { slot5Module 1 }  

slot5ModuleEntry OBJECT-TYPE
    SYNTAX      Slot5ModuleEntry
    MAX-ACCESS  not-accessible
    STATUS      current
    DESCRIPTION
            "An entry contains a slot5Module's utilization."
    INDEX   { slot5ModuleIndex }
    ::= { slot5ModuleTable 1 }

Slot5ModuleEntry ::=
    SEQUENCE {     
		slot5ModuleIndex                       Integer32,
		slot5ModuleId                           DisplayString,  
		slot5ModuleIfNumber                     Integer32		
    } 

slot5ModuleIndex OBJECT-TYPE
    SYNTAX      Integer32 (1..2147483647)
    MAX-ACCESS  not-accessible
    STATUS      current
    DESCRIPTION
            "A unique value, greater than zero, for each chassis`s slot5."
    ::= { slot5ModuleEntry 1 }

slot5ModuleId OBJECT-TYPE
    SYNTAX      DisplayString (SIZE (0..32))
    MAX-ACCESS  read-only
    STATUS      current
    DESCRIPTION
            "the value of module`s id"
    ::= { slot5ModuleEntry 2 }
  
slot5ModuleIfNumber OBJECT-TYPE
    SYNTAX      Integer32(0..2147483647)
    MAX-ACCESS  read-only
    STATUS      current
    DESCRIPTION
            "The number of network interfaces (regardless of their
            current state) present on this system." 
    ::= { slot5ModuleEntry 3 } 
    
slot5ModuleIfTable OBJECT-TYPE
    SYNTAX      SEQUENCE OF Slot5ModuleIfEntry
    MAX-ACCESS  not-accessible
    STATUS      current
    DESCRIPTION
            "A list of interface entries.  The number of entries is
            given by the value of ifNumber."
    ::= { slot5Module 2 } 
    
slot5ModuleIfEntry OBJECT-TYPE
    SYNTAX      Slot5ModuleIfEntry
    MAX-ACCESS  not-accessible
    STATUS      current
    DESCRIPTION
            "An entry containing management information applicable to a
            particular interface."
    INDEX   { slot5ModuleifIndex }
    ::= { slot5ModuleIfTable 1 }
    
Slot5ModuleIfEntry ::=
    SEQUENCE {
        slot5ModuleifIndex                 InterfaceIndex,  
        slot5ModuleIfId                    DisplayString,  
        slot5ModuleifDescr                 DisplayString,           
        slot5ModuleifType                  IANAifType,   		
        slot5ModuleifMtu                   Integer32,                
        slot5ModuleifSpeed                 Counter64,               
        slot5ModuleifPhysAddress           PhysAddress,              
        slot5ModuleifAdminStatus           INTEGER,                  
        slot5ModuleifOperStatus            INTEGER,                  
        slot5ModuleifLastChange            TimeTicks,                
	slot5ModuleifInKbits   	           Counter64,
	slot5ModuleifOutKbits              Counter64,
        slot5ModuleifInOctets              Counter64,                
        slot5ModuleifInUcastPkts           Counter64,                
        slot5ModuleifInNUcastPkts          Counter64,  
        slot5ModuleifInDiscards            Counter64,
        slot5ModuleifInErrors              Counter64,
        slot5ModuleifInFcsErrorPkts        Counter64,
        slot5ModuleifInUnknownProtos       Counter64,	-- deprecated
        slot5ModuleifOutOctets             Counter64,
        slot5ModuleifOutUcastPkts          Counter64,
        slot5ModuleifOutNUcastPkts         Counter64,  -- deprecated
        slot5ModuleifOutDiscards           Counter64,
        slot5ModuleifOutErrors             Counter64,
        slot5ModuleifOutFcsErrorPkts       Counter64,
        slot5ModuleifOutQLen               Gauge32,    -- deprecated  
	    slot5ModuleifInpps   	           Counter64,
	    slot5ModuleifOutpps              Counter64,        
        slot5ModuleifRxPower                DisplayString,
        slot5ModuleifTxPower                DisplayString,
        slot5ModuleifSpecific              OBJECT IDENTIFIER
    }         

slot5ModuleifIndex OBJECT-TYPE
    SYNTAX      InterfaceIndex
    MAX-ACCESS  read-only
    STATUS      current
    DESCRIPTION
            "A unique value, greater than zero, for each interface.  It
            is recommended that values are assigned contiguously
            starting from 1.  The value for each interface sub-layer
            must remain constant at least from one re-initialization of
            the entity's network management system to the next re-
            initialization."
    ::= { slot5ModuleIfEntry 1 }
    
slot5ModuleIfId OBJECT-TYPE
    SYNTAX      DisplayString (SIZE (0..32))
    MAX-ACCESS  read-only
    STATUS      current
    DESCRIPTION
            "the value of module`s id"
    ::= { slot5ModuleIfEntry 2 }
    
slot5ModuleifDescr OBJECT-TYPE
    SYNTAX      DisplayString (SIZE (0..255))
    MAX-ACCESS  read-only
    STATUS      current
    DESCRIPTION
            "A textual string containing information about the
            interface.  This string should include the name of the
            manufacturer, the product name and the version of the
            interface hardware/software."
    ::= { slot5ModuleIfEntry 3 }
    
slot5ModuleifType OBJECT-TYPE
    SYNTAX      IANAifType
    MAX-ACCESS  read-only
    STATUS      current
    DESCRIPTION
            "The type of interface.  Additional values for ifType are
            assigned by the Internet Assigned Numbers Authority (IANA),
            through updating the syntax of the IANAifType textual
            convention."
    ::= { slot5ModuleIfEntry 4 }

slot5ModuleifMtu OBJECT-TYPE
    SYNTAX      Integer32(1..2147483647)
    MAX-ACCESS  read-only
    STATUS      current
    DESCRIPTION
            "The size of the largest packet which can be sent/received
            on the interface, specified in octets.  For interfaces that
            are used for transmitting network datagrams, this is the
            size of the largest network datagram that can be sent on the
            interface."
    ::= { slot5ModuleIfEntry 5 }

slot5ModuleifSpeed OBJECT-TYPE
    SYNTAX      Counter64
    MAX-ACCESS  read-only
    STATUS      current
    DESCRIPTION
            "An estimate of the interface's current bandwidth in bits
            per second.  For interfaces which do not vary in bandwidth
            or for those where no accurate estimation can be made, this
            object should contain the nominal bandwidth. For a sub-layer
            which has no concept of bandwidth, this object should be zero."
    ::= { slot5ModuleIfEntry 6 }

slot5ModuleifPhysAddress OBJECT-TYPE
    SYNTAX      PhysAddress
    MAX-ACCESS  read-only
    STATUS      current
    DESCRIPTION
            "The interface's address at its protocol sub-layer.  For
            example, for an 802.x interface, this object normally
            contains a MAC address.  The interface's media-specific MIB
            must define the bit and byte ordering and the format of the
            value of this object.  For interfaces which do not have such
            an address (e.g., a serial line), this object should contain
            an octet string of zero length."
    ::= { slot5ModuleIfEntry 7 }
    
slot5ModuleifAdminStatus OBJECT-TYPE
    SYNTAX  INTEGER {
                up(1),       -- ready to pass packets
                down(2),
                testing(3)   -- in some test mode
            }
    MAX-ACCESS  read-write
    STATUS      current
    DESCRIPTION
            "The desired state of the interface.  The testing(3) state
            indicates that no operational packets can be passed.  When a
            managed system initializes, all interfaces start with
            ifAdminStatus in the down(2) state.  As a result of either
            explicit management action or per configuration information
            retained by the managed system, ifAdminStatus is then
            changed to either the up(1) or testing(3) states (or remains
            in the down(2) state)."
    ::= { slot5ModuleIfEntry 8 }

slot5ModuleifOperStatus OBJECT-TYPE
    SYNTAX  INTEGER {
                up(1),        -- ready to pass packets
                down(2),
                testing(3),   -- in some test mode
                unknown(4),   -- status can not be determined
                              -- for some reason.
                dormant(5),
                notPresent(6),    -- some component is missing
                lowerLayerDown(7) -- down due to state of
                                  -- lower-layer interface(s)
            }
    MAX-ACCESS  read-only
    STATUS      current
    DESCRIPTION
            "The current operational state of the interface.  The
            testing(3) state indicates that no operational packets can
            be passed.  If ifAdminStatus is down(2) then ifOperStatus
            should be down(2).  If ifAdminStatus is changed to up(1)
            then ifOperStatus should change to up(1) if the interface is
            ready to transmit and receive network traffic; it should
            change to dormant(5) if the interface is waiting for
            external actions (such as a serial line waiting for an
            incoming connection); it should remain in the down(2) state
            if and only if there is a fault that prevents it from going
            to the up(1) state; it should remain in the notPresent(6)
            state if the interface has missing (typically, hardware)
            components."
    ::= { slot5ModuleIfEntry 9 }

slot5ModuleifLastChange OBJECT-TYPE
    SYNTAX      TimeTicks
    MAX-ACCESS  read-only
    STATUS      current
    DESCRIPTION
            "The value of sysUpTime at the time the interface entered
            its current operational state.  If the current state was
            entered prior to the last re-initialization of the local
            network management subsystem, then this object contains a
            zero value."
    ::= { slot5ModuleIfEntry 10 }

slot5ModuleifInKbits OBJECT-TYPE
    SYNTAX      Counter64
    MAX-ACCESS  read-only
    STATUS      current
    DESCRIPTION
            "The real time rate received on the interface, in Kbits
	    format.

            Discontinuities in the value of this counter can occur at
            re-initialization of the management system, and at other
            times as indicated by the value of
            ifCounterDiscontinuityTime."
    ::= { slot5ModuleIfEntry 11 }

slot5ModuleifOutKbits OBJECT-TYPE
    SYNTAX      Counter64
    MAX-ACCESS  read-only
    STATUS      current
    DESCRIPTION
            "The real time rate send on the interface, in Kbits
	    format.

            Discontinuities in the value of this counter can occur at
            re-initialization of the management system, and at other
            times as indicated by the value of
            ifCounterDiscontinuityTime."
    ::= { slot5ModuleIfEntry 12 }

slot5ModuleifInOctets OBJECT-TYPE
    SYNTAX      Counter64
    MAX-ACCESS  read-only
    STATUS      current
    DESCRIPTION
            "The total number of octets received on the interface,
            including framing characters.

            Discontinuities in the value of this counter can occur at
            re-initialization of the management system, and at other
            times as indicated by the value of
            ifCounterDiscontinuityTime."
    ::= { slot5ModuleIfEntry 13 }

slot5ModuleifInUcastPkts OBJECT-TYPE
    SYNTAX      Counter64
    MAX-ACCESS  read-only
    STATUS      current
    DESCRIPTION
            "The number of packets, delivered by this sub-layer to a
            higher (sub-)layer, which were not addressed to a multicast
            or broadcast address at this sub-layer.

            Discontinuities in the value of this counter can occur at
            re-initialization of the management system, and at other
            times as indicated by the value of
            ifCounterDiscontinuityTime."
    ::= { slot5ModuleIfEntry 14 }

slot5ModuleifInNUcastPkts OBJECT-TYPE
    SYNTAX  Counter64
    MAX-ACCESS  read-only
    STATUS      current
    DESCRIPTION
            "The number of packets, delivered by this sub-layer to a
            higher (sub-)layer, which were addressed to a multicast or
            broadcast address at this sub-layer.

            Discontinuities in the value of this counter can occur at
            re-initialization of the management system, and at other
            times as indicated by the value of
            ifCounterDiscontinuityTime.

            This object is deprecated in favour of ifInMulticastPkts and
            ifInBroadcastPkts."
    ::= { slot5ModuleIfEntry 15 }

slot5ModuleifInDiscards OBJECT-TYPE
    SYNTAX      Counter64
    MAX-ACCESS  read-only
    STATUS      current
    DESCRIPTION
            "The number of inbound packets which were chosen to be
            discarded even though no errors had been detected to prevent

            their being deliverable to a higher-layer protocol.  One
            possible reason for discarding such a packet could be to
            free up buffer space.

            Discontinuities in the value of this counter can occur at
            re-initialization of the management system, and at other
            times as indicated by the value of
            ifCounterDiscontinuityTime."
    ::= { slot5ModuleIfEntry 16 }

slot5ModuleifInErrors OBJECT-TYPE
    SYNTAX      Counter64
    MAX-ACCESS  read-only
    STATUS      current
    DESCRIPTION
            "For packet-oriented interfaces, the number of inbound
            packets that contained errors preventing them from being
            deliverable to a higher-layer protocol.  For character-
            oriented or fixed-length interfaces, the number of inbound
            transmission units that contained errors preventing them
            from being deliverable to a higher-layer protocol.

            Discontinuities in the value of this counter can occur at
            re-initialization of the management system, and at other
            times as indicated by the value of
            ifCounterDiscontinuityTime."
    ::= { slot5ModuleIfEntry 17 }

slot5ModuleifInFcsErrorPkts OBJECT-TYPE
    SYNTAX      Counter64
    MAX-ACCESS  read-only
    STATUS      current
    DESCRIPTION
            "FCS error pakets."
    ::= { slot5ModuleIfEntry 18 }

slot5ModuleifInUnknownProtos OBJECT-TYPE
    SYNTAX      Counter64
    MAX-ACCESS  read-only
    STATUS      current
    DESCRIPTION
            "For packet-oriented interfaces, the number of packets
            received via the interface which were discarded because of
            an unknown or unsupported protocol.  For character-oriented
            or fixed-length interfaces that support protocol
            multiplexing the number of transmission units received via
            the interface which were discarded because of an unknown or
            unsupported protocol.  For any interface that does not
            support protocol multiplexing, this counter will always be
            0.

            Discontinuities in the value of this counter can occur at
            re-initialization of the management system, and at other
            times as indicated by the value of
            ifCounterDiscontinuityTime."
    ::= { slot5ModuleIfEntry 19 }

slot5ModuleifOutOctets OBJECT-TYPE
    SYNTAX      Counter64
    MAX-ACCESS  read-only
    STATUS      current
    DESCRIPTION
            "The total number of octets transmitted out of the
            interface, including framing characters.

            Discontinuities in the value of this counter can occur at
            re-initialization of the management system, and at other
            times as indicated by the value of
            ifCounterDiscontinuityTime."
    ::= { slot5ModuleIfEntry 20 }

slot5ModuleifOutUcastPkts OBJECT-TYPE
    SYNTAX      Counter64
    MAX-ACCESS  read-only
    STATUS      current
    DESCRIPTION
            "The total number of packets that higher-level protocols
            requested be transmitted, and which were not addressed to a
            multicast or broadcast address at this sub-layer, including
            those that were discarded or not sent.

            Discontinuities in the value of this counter can occur at
            re-initialization of the management system, and at other
            times as indicated by the value of
            ifCounterDiscontinuityTime."
    ::= { slot5ModuleIfEntry 21 }

slot5ModuleifOutNUcastPkts OBJECT-TYPE
    SYNTAX      Counter64
    MAX-ACCESS  read-only
    STATUS      deprecated
    DESCRIPTION
            "The total number of packets that higher-level protocols
            requested be transmitted, and which were addressed to a
            multicast or broadcast address at this sub-layer, including
            those that were discarded or not sent.

            Discontinuities in the value of this counter can occur at
            re-initialization of the management system, and at other
            times as indicated by the value of
            ifCounterDiscontinuityTime.

            This object is deprecated in favour of ifOutMulticastPkts
            and ifOutBroadcastPkts."
    ::= { slot5ModuleIfEntry 22 }

slot5ModuleifOutDiscards OBJECT-TYPE
    SYNTAX      Counter64
    MAX-ACCESS  read-only
    STATUS      current
    DESCRIPTION
            "The number of outbound packets which were chosen to be
            discarded even though no errors had been detected to prevent
            their being transmitted.  One possible reason for discarding
            such a packet could be to free up buffer space.

            Discontinuities in the value of this counter can occur at
            re-initialization of the management system, and at other
            times as indicated by the value of
            ifCounterDiscontinuityTime."
    ::= { slot5ModuleIfEntry 23 }

slot5ModuleifOutErrors OBJECT-TYPE
    SYNTAX      Counter64
    MAX-ACCESS  read-only
    STATUS      current
    DESCRIPTION
            "For packet-oriented interfaces, the number of outbound
            packets that could not be transmitted because of errors.
            For character-oriented or fixed-length interfaces, the
            number of outbound transmission units that could not be
            transmitted because of errors.

            Discontinuities in the value of this counter can occur at
            re-initialization of the management system, and at other
            times as indicated by the value of
            ifCounterDiscontinuityTime."
    ::= { slot5ModuleIfEntry 24 }

slot5ModuleifOutFcsErrorPkts OBJECT-TYPE
    SYNTAX      Counter64
    MAX-ACCESS  read-only
    STATUS      current
    DESCRIPTION
            "FCS error pakets."
    ::= { slot5ModuleIfEntry 25 }

slot5ModuleifOutQLen OBJECT-TYPE
    SYNTAX      Gauge32
    MAX-ACCESS  read-only
    STATUS      deprecated
    DESCRIPTION
            "The length of the output packet queue (in packets)."
    ::= { slot5ModuleIfEntry 26 }

slot5ModuleifInpps OBJECT-TYPE
    SYNTAX      Counter64
    MAX-ACCESS  read-only
    STATUS      current
    DESCRIPTION
            "The real time rate received on the interface, in pps
	    format.

            Discontinuities in the value of this counter can occur at
            re-initialization of the management system, and at other
            times as indicated by the value of
            ifCounterDiscontinuityTime."
    ::= { slot5ModuleIfEntry 27 }

slot5ModuleifOutpps OBJECT-TYPE
    SYNTAX      Counter64
    MAX-ACCESS  read-only
    STATUS      current
    DESCRIPTION
            "The real time rate send on the interface, in pps
	    format.

            Discontinuities in the value of this counter can occur at
            re-initialization of the management system, and at other
            times as indicated by the value of
            ifCounterDiscontinuityTime."
    ::= { slot5ModuleIfEntry 28 }

slot5ModuleifRxPower OBJECT-TYPE
    SYNTAX      DisplayString (SIZE (0..255))
    MAX-ACCESS  read-only
    STATUS      current
    DESCRIPTION
            "the value of interface's received power, in dbm format."
    ::= { slot5ModuleIfEntry 29 }
    
slot5ModuleifTxPower OBJECT-TYPE
    SYNTAX      DisplayString (SIZE (0..255))
    MAX-ACCESS  read-only
    STATUS      current
    DESCRIPTION
            "the value of interface's send power, in dbm format."
    ::= { slot5ModuleIfEntry 30 }

slot5ModuleifSpecific OBJECT-TYPE
    SYNTAX      OBJECT IDENTIFIER
    MAX-ACCESS  read-only
    STATUS      deprecated
    DESCRIPTION
            "A reference to MIB definitions specific to the particular
            media being used to realize the interface.  It is

            recommended that this value point to an instance of a MIB
            object in the media-specific MIB, i.e., that this object
            have the semantics associated with the InstancePointer
            textual convention defined in RFC 2579.  In fact, it is
            recommended that the media-specific MIB specify what value
            ifSpecific should/can take for values of ifType.  If no MIB
            definitions specific to the particular media are available,
            the value should be set to the OBJECT IDENTIFIER { 0 0 }."
    ::= { slot5ModuleIfEntry 31 }  

-- slot 6 --

-- slot6Table --

slot6Table OBJECT-TYPE
    SYNTAX      SEQUENCE OF Slot6Entry
    MAX-ACCESS  not-accessible
    STATUS      current
    DESCRIPTION
            "A list of all slot6Type's utilization."
    ::= { slot6 1 }  

slot6Entry OBJECT-TYPE
    SYNTAX      Slot6Entry
    MAX-ACCESS  not-accessible
    STATUS      current
    DESCRIPTION
            "An entry contains a slot6's utilization."
    INDEX   { slot6Index }
    ::= { slot6Table 1 }

Slot6Entry ::=
    SEQUENCE {     
		slot6Index                       Integer32,
		slot6Type                        DisplayString,
		slot6Status                      DisplayString,		
		slot6Id                          Integer32
    }  

slot6Index OBJECT-TYPE
    SYNTAX      Integer32 (1..2147483647)
    MAX-ACCESS  not-accessible
    STATUS      current
    DESCRIPTION
            "A unique value, greater than zero, for each chassis`s slot6."
    ::= { slot6Entry 1 }

slot6Type OBJECT-TYPE
    SYNTAX      DisplayString (SIZE (0..255))
    MAX-ACCESS  read-only
    STATUS      current
    DESCRIPTION
            "the slot6Type of each chassis."
    ::= { slot6Entry 2 }

slot6Status OBJECT-TYPE
    SYNTAX      DisplayString (SIZE (0..255))
    MAX-ACCESS  read-only
    STATUS      current
    DESCRIPTION
            "A string to describe the board status." 
    ::= { slot6Entry 3 }   

slot6Id OBJECT-TYPE
    SYNTAX      Integer32
    MAX-ACCESS  read-only
    STATUS      current
    DESCRIPTION
            "slot id."
    ::= { slot6Entry 4 }

slot6Module OBJECT IDENTIFIER ::= { slot6 2 }

-- slot6ModuleTable --
slot6ModuleTable OBJECT-TYPE
    SYNTAX      SEQUENCE OF Slot6ModuleEntry
    MAX-ACCESS  not-accessible
    STATUS      current
    DESCRIPTION
            "A list of all slot6Module's utilization."
    ::= { slot6Module 1 }  

slot6ModuleEntry OBJECT-TYPE
    SYNTAX      Slot6ModuleEntry
    MAX-ACCESS  not-accessible
    STATUS      current
    DESCRIPTION
            "An entry contains a slot6Module's utilization."
    INDEX   { slot6ModuleIndex }
    ::= { slot6ModuleTable 1 }

Slot6ModuleEntry ::=
    SEQUENCE {     
		slot6ModuleIndex                       Integer32,
		slot6ModuleId                           DisplayString,  
		slot6ModuleIfNumber                     Integer32		
    } 

slot6ModuleIndex OBJECT-TYPE
    SYNTAX      Integer32 (1..2147483647)
    MAX-ACCESS  not-accessible
    STATUS      current
    DESCRIPTION
            "A unique value, greater than zero, for each chassis`s slot6."
    ::= { slot6ModuleEntry 1 }

slot6ModuleId OBJECT-TYPE
    SYNTAX      DisplayString (SIZE (0..32))
    MAX-ACCESS  read-only
    STATUS      current
    DESCRIPTION
            "the value of module`s id"
    ::= { slot6ModuleEntry 2 }
  
slot6ModuleIfNumber OBJECT-TYPE
    SYNTAX      Integer32(0..2147483647)
    MAX-ACCESS  read-only
    STATUS      current
    DESCRIPTION
            "The number of network interfaces (regardless of their
            current state) present on this system." 
    ::= { slot6ModuleEntry 3 } 
    
slot6ModuleIfTable OBJECT-TYPE
    SYNTAX      SEQUENCE OF Slot6ModuleIfEntry
    MAX-ACCESS  not-accessible
    STATUS      current
    DESCRIPTION
            "A list of interface entries.  The number of entries is
            given by the value of ifNumber."
    ::= { slot6Module 2 } 
    
slot6ModuleIfEntry OBJECT-TYPE
    SYNTAX      Slot6ModuleIfEntry
    MAX-ACCESS  not-accessible
    STATUS      current
    DESCRIPTION
            "An entry containing management information applicable to a
            particular interface."
    INDEX   { slot6ModuleifIndex }
    ::= { slot6ModuleIfTable 1 }
    
Slot6ModuleIfEntry ::=
    SEQUENCE {
        slot6ModuleifIndex                 InterfaceIndex,  
        slot6ModuleIfId                    DisplayString,  
        slot6ModuleifDescr                 DisplayString,           
        slot6ModuleifType                  IANAifType,   		
        slot6ModuleifMtu                   Integer32,                
        slot6ModuleifSpeed                 Counter64,               
        slot6ModuleifPhysAddress           PhysAddress,              
        slot6ModuleifAdminStatus           INTEGER,                  
        slot6ModuleifOperStatus            INTEGER,                  
        slot6ModuleifLastChange            TimeTicks,                
	slot6ModuleifInKbits   	           Counter64,
	slot6ModuleifOutKbits              Counter64,
        slot6ModuleifInOctets              Counter64,                
        slot6ModuleifInUcastPkts           Counter64,                
        slot6ModuleifInNUcastPkts          Counter64,   
        slot6ModuleifInDiscards            Counter64,
        slot6ModuleifInErrors              Counter64,
        slot6ModuleifInFcsErrorPkts        Counter64,
        slot6ModuleifInUnknownProtos       Counter64,	-- deprecated
        slot6ModuleifOutOctets             Counter64,
        slot6ModuleifOutUcastPkts          Counter64,
        slot6ModuleifOutNUcastPkts         Counter64,  -- deprecated
        slot6ModuleifOutDiscards           Counter64,
        slot6ModuleifOutErrors             Counter64,
        slot6ModuleifOutFcsErrorPkts       Counter64,
        slot6ModuleifOutQLen               Gauge32,    -- deprecated  
	    slot6ModuleifInpps   	           Counter64,
	    slot6ModuleifOutpps              Counter64,        
        slot6ModuleifRxPower                DisplayString,
        slot6ModuleifTxPower                DisplayString,
        slot6ModuleifSpecific              OBJECT IDENTIFIER
    }         

slot6ModuleifIndex OBJECT-TYPE
    SYNTAX      InterfaceIndex
    MAX-ACCESS  read-only
    STATUS      current
    DESCRIPTION
            "A unique value, greater than zero, for each interface.  It
            is recommended that values are assigned contiguously
            starting from 1.  The value for each interface sub-layer
            must remain constant at least from one re-initialization of
            the entity's network management system to the next re-
            initialization."
    ::= { slot6ModuleIfEntry 1 }
    
slot6ModuleIfId OBJECT-TYPE
    SYNTAX      DisplayString (SIZE (0..32))
    MAX-ACCESS  read-only
    STATUS      current
    DESCRIPTION
            "the value of module`s id"
    ::= { slot6ModuleIfEntry 2 }
    
slot6ModuleifDescr OBJECT-TYPE
    SYNTAX      DisplayString (SIZE (0..255))
    MAX-ACCESS  read-only
    STATUS      current
    DESCRIPTION
            "A textual string containing information about the
            interface.  This string should include the name of the
            manufacturer, the product name and the version of the
            interface hardware/software."
    ::= { slot6ModuleIfEntry 3 }
    
slot6ModuleifType OBJECT-TYPE
    SYNTAX      IANAifType
    MAX-ACCESS  read-only
    STATUS      current
    DESCRIPTION
            "The type of interface.  Additional values for ifType are
            assigned by the Internet Assigned Numbers Authority (IANA),
            through updating the syntax of the IANAifType textual
            convention."
    ::= { slot6ModuleIfEntry 4 }

slot6ModuleifMtu OBJECT-TYPE
    SYNTAX      Integer32(1..2147483647)
    MAX-ACCESS  read-only
    STATUS      current
    DESCRIPTION
            "The size of the largest packet which can be sent/received
            on the interface, specified in octets.  For interfaces that
            are used for transmitting network datagrams, this is the
            size of the largest network datagram that can be sent on the
            interface."
    ::= { slot6ModuleIfEntry 5 }

slot6ModuleifSpeed OBJECT-TYPE
    SYNTAX      Counter64
    MAX-ACCESS  read-only
    STATUS      current
    DESCRIPTION
            "An estimate of the interface's current bandwidth in bits
            per second.  For interfaces which do not vary in bandwidth
            or for those where no accurate estimation can be made, this
            object should contain the nominal bandwidth. For a sub-layer
            which has no concept of bandwidth, this object should be zero."
    ::= { slot6ModuleIfEntry 6 }

slot6ModuleifPhysAddress OBJECT-TYPE
    SYNTAX      PhysAddress
    MAX-ACCESS  read-only
    STATUS      current
    DESCRIPTION
            "The interface's address at its protocol sub-layer.  For
            example, for an 802.x interface, this object normally
            contains a MAC address.  The interface's media-specific MIB
            must define the bit and byte ordering and the format of the
            value of this object.  For interfaces which do not have such
            an address (e.g., a serial line), this object should contain
            an octet string of zero length."
    ::= { slot6ModuleIfEntry 7 }
    
slot6ModuleifAdminStatus OBJECT-TYPE
    SYNTAX  INTEGER {
                up(1),       -- ready to pass packets
                down(2),
                testing(3)   -- in some test mode
            }
    MAX-ACCESS  read-write
    STATUS      current
    DESCRIPTION
            "The desired state of the interface.  The testing(3) state
            indicates that no operational packets can be passed.  When a
            managed system initializes, all interfaces start with
            ifAdminStatus in the down(2) state.  As a result of either
            explicit management action or per configuration information
            retained by the managed system, ifAdminStatus is then
            changed to either the up(1) or testing(3) states (or remains
            in the down(2) state)."
    ::= { slot6ModuleIfEntry 8 }

slot6ModuleifOperStatus OBJECT-TYPE
    SYNTAX  INTEGER {
                up(1),        -- ready to pass packets
                down(2),
                testing(3),   -- in some test mode
                unknown(4),   -- status can not be determined
                              -- for some reason.
                dormant(5),
                notPresent(6),    -- some component is missing
                lowerLayerDown(7) -- down due to state of
                                  -- lower-layer interface(s)
            }
    MAX-ACCESS  read-only
    STATUS      current
    DESCRIPTION
            "The current operational state of the interface.  The
            testing(3) state indicates that no operational packets can
            be passed.  If ifAdminStatus is down(2) then ifOperStatus
            should be down(2).  If ifAdminStatus is changed to up(1)
            then ifOperStatus should change to up(1) if the interface is
            ready to transmit and receive network traffic; it should
            change to dormant(5) if the interface is waiting for
            external actions (such as a serial line waiting for an
            incoming connection); it should remain in the down(2) state
            if and only if there is a fault that prevents it from going
            to the up(1) state; it should remain in the notPresent(6)
            state if the interface has missing (typically, hardware)
            components."
    ::= { slot6ModuleIfEntry 9 }

slot6ModuleifLastChange OBJECT-TYPE
    SYNTAX      TimeTicks
    MAX-ACCESS  read-only
    STATUS      current
    DESCRIPTION
            "The value of sysUpTime at the time the interface entered
            its current operational state.  If the current state was
            entered prior to the last re-initialization of the local
            network management subsystem, then this object contains a
            zero value."
    ::= { slot6ModuleIfEntry 10 }

slot6ModuleifInKbits OBJECT-TYPE
    SYNTAX      Counter64
    MAX-ACCESS  read-only
    STATUS      current
    DESCRIPTION
            "The real time rate received on the interface, in Kbits
	    format.

            Discontinuities in the value of this counter can occur at
            re-initialization of the management system, and at other
            times as indicated by the value of
            ifCounterDiscontinuityTime."
    ::= { slot6ModuleIfEntry 11 }

slot6ModuleifOutKbits OBJECT-TYPE
    SYNTAX      Counter64
    MAX-ACCESS  read-only
    STATUS      current
    DESCRIPTION
            "The real time rate send on the interface, in Kbits
	    format.

            Discontinuities in the value of this counter can occur at
            re-initialization of the management system, and at other
            times as indicated by the value of
            ifCounterDiscontinuityTime."
    ::= { slot6ModuleIfEntry 12 }

slot6ModuleifInOctets OBJECT-TYPE
    SYNTAX      Counter64
    MAX-ACCESS  read-only
    STATUS      current
    DESCRIPTION
            "The total number of octets received on the interface,
            including framing characters.

            Discontinuities in the value of this counter can occur at
            re-initialization of the management system, and at other
            times as indicated by the value of
            ifCounterDiscontinuityTime."
    ::= { slot6ModuleIfEntry 13 }

slot6ModuleifInUcastPkts OBJECT-TYPE
    SYNTAX      Counter64
    MAX-ACCESS  read-only
    STATUS      current
    DESCRIPTION
            "The number of packets, delivered by this sub-layer to a
            higher (sub-)layer, which were not addressed to a multicast
            or broadcast address at this sub-layer.

            Discontinuities in the value of this counter can occur at
            re-initialization of the management system, and at other
            times as indicated by the value of
            ifCounterDiscontinuityTime."
    ::= { slot6ModuleIfEntry 14 }

slot6ModuleifInNUcastPkts OBJECT-TYPE
    SYNTAX  Counter64
    MAX-ACCESS  read-only
    STATUS      current
    DESCRIPTION
            "The number of packets, delivered by this sub-layer to a
            higher (sub-)layer, which were addressed to a multicast or
            broadcast address at this sub-layer.

            Discontinuities in the value of this counter can occur at
            re-initialization of the management system, and at other
            times as indicated by the value of
            ifCounterDiscontinuityTime.

            This object is deprecated in favour of ifInMulticastPkts and
            ifInBroadcastPkts."
    ::= { slot6ModuleIfEntry 15 }

slot6ModuleifInDiscards OBJECT-TYPE
    SYNTAX      Counter64
    MAX-ACCESS  read-only
    STATUS      current
    DESCRIPTION
            "The number of inbound packets which were chosen to be
            discarded even though no errors had been detected to prevent

            their being deliverable to a higher-layer protocol.  One
            possible reason for discarding such a packet could be to
            free up buffer space.

            Discontinuities in the value of this counter can occur at
            re-initialization of the management system, and at other
            times as indicated by the value of
            ifCounterDiscontinuityTime."
    ::= { slot6ModuleIfEntry 16 }

slot6ModuleifInErrors OBJECT-TYPE
    SYNTAX      Counter64
    MAX-ACCESS  read-only
    STATUS      current
    DESCRIPTION
            "For packet-oriented interfaces, the number of inbound
            packets that contained errors preventing them from being
            deliverable to a higher-layer protocol.  For character-
            oriented or fixed-length interfaces, the number of inbound
            transmission units that contained errors preventing them
            from being deliverable to a higher-layer protocol.

            Discontinuities in the value of this counter can occur at
            re-initialization of the management system, and at other
            times as indicated by the value of
            ifCounterDiscontinuityTime."
    ::= { slot6ModuleIfEntry 17 }

slot6ModuleifInFcsErrorPkts OBJECT-TYPE
    SYNTAX      Counter64
    MAX-ACCESS  read-only
    STATUS      current
    DESCRIPTION
            "FCS error pakets."
    ::= { slot6ModuleIfEntry 18 }

slot6ModuleifInUnknownProtos OBJECT-TYPE
    SYNTAX      Counter64
    MAX-ACCESS  read-only
    STATUS      current
    DESCRIPTION
            "For packet-oriented interfaces, the number of packets
            received via the interface which were discarded because of
            an unknown or unsupported protocol.  For character-oriented
            or fixed-length interfaces that support protocol
            multiplexing the number of transmission units received via
            the interface which were discarded because of an unknown or
            unsupported protocol.  For any interface that does not
            support protocol multiplexing, this counter will always be
            0.

            Discontinuities in the value of this counter can occur at
            re-initialization of the management system, and at other
            times as indicated by the value of
            ifCounterDiscontinuityTime."
    ::= { slot6ModuleIfEntry 19 }

slot6ModuleifOutOctets OBJECT-TYPE
    SYNTAX      Counter64
    MAX-ACCESS  read-only
    STATUS      current
    DESCRIPTION
            "The total number of octets transmitted out of the
            interface, including framing characters.

            Discontinuities in the value of this counter can occur at
            re-initialization of the management system, and at other
            times as indicated by the value of
            ifCounterDiscontinuityTime."
    ::= { slot6ModuleIfEntry 20 }

slot6ModuleifOutUcastPkts OBJECT-TYPE
    SYNTAX      Counter64
    MAX-ACCESS  read-only
    STATUS      current
    DESCRIPTION
            "The total number of packets that higher-level protocols
            requested be transmitted, and which were not addressed to a
            multicast or broadcast address at this sub-layer, including
            those that were discarded or not sent.

            Discontinuities in the value of this counter can occur at
            re-initialization of the management system, and at other
            times as indicated by the value of
            ifCounterDiscontinuityTime."
    ::= { slot6ModuleIfEntry 21 }

slot6ModuleifOutNUcastPkts OBJECT-TYPE
    SYNTAX      Counter64
    MAX-ACCESS  read-only
    STATUS      deprecated
    DESCRIPTION
            "The total number of packets that higher-level protocols
            requested be transmitted, and which were addressed to a
            multicast or broadcast address at this sub-layer, including
            those that were discarded or not sent.

            Discontinuities in the value of this counter can occur at
            re-initialization of the management system, and at other
            times as indicated by the value of
            ifCounterDiscontinuityTime.

            This object is deprecated in favour of ifOutMulticastPkts
            and ifOutBroadcastPkts."
    ::= { slot6ModuleIfEntry 22 }

slot6ModuleifOutDiscards OBJECT-TYPE
    SYNTAX      Counter64
    MAX-ACCESS  read-only
    STATUS      current
    DESCRIPTION
            "The number of outbound packets which were chosen to be
            discarded even though no errors had been detected to prevent
            their being transmitted.  One possible reason for discarding
            such a packet could be to free up buffer space.

            Discontinuities in the value of this counter can occur at
            re-initialization of the management system, and at other
            times as indicated by the value of
            ifCounterDiscontinuityTime."
    ::= { slot6ModuleIfEntry 23 }

slot6ModuleifOutErrors OBJECT-TYPE
    SYNTAX      Counter64
    MAX-ACCESS  read-only
    STATUS      current
    DESCRIPTION
            "For packet-oriented interfaces, the number of outbound
            packets that could not be transmitted because of errors.
            For character-oriented or fixed-length interfaces, the
            number of outbound transmission units that could not be
            transmitted because of errors.

            Discontinuities in the value of this counter can occur at
            re-initialization of the management system, and at other
            times as indicated by the value of
            ifCounterDiscontinuityTime."
    ::= { slot6ModuleIfEntry 24 }

slot6ModuleifOutFcsErrorPkts OBJECT-TYPE
    SYNTAX      Counter64
    MAX-ACCESS  read-only
    STATUS      current
    DESCRIPTION
            "FCS error pakets."
    ::= { slot6ModuleIfEntry 25 }

slot6ModuleifOutQLen OBJECT-TYPE
    SYNTAX      Gauge32
    MAX-ACCESS  read-only
    STATUS      deprecated
    DESCRIPTION
            "The length of the output packet queue (in packets)."
    ::= { slot6ModuleIfEntry 26 }

slot6ModuleifInpps OBJECT-TYPE
    SYNTAX      Counter64
    MAX-ACCESS  read-only
    STATUS      current
    DESCRIPTION
            "The real time rate received on the interface, in pps
	    format.

            Discontinuities in the value of this counter can occur at
            re-initialization of the management system, and at other
            times as indicated by the value of
            ifCounterDiscontinuityTime."
    ::= { slot6ModuleIfEntry 27 }

slot6ModuleifOutpps OBJECT-TYPE
    SYNTAX      Counter64
    MAX-ACCESS  read-only
    STATUS      current
    DESCRIPTION
            "The real time rate send on the interface, in pps
	    format.

            Discontinuities in the value of this counter can occur at
            re-initialization of the management system, and at other
            times as indicated by the value of
            ifCounterDiscontinuityTime."
    ::= { slot6ModuleIfEntry 28 }
    
slot6ModuleifRxPower OBJECT-TYPE
    SYNTAX      DisplayString (SIZE (0..255))
    MAX-ACCESS  read-only
    STATUS      current
    DESCRIPTION
            "the value of interface's received power, in dbm format."
    ::= { slot6ModuleIfEntry 29 }
    
slot6ModuleifTxPower OBJECT-TYPE
    SYNTAX      DisplayString (SIZE (0..255))
    MAX-ACCESS  read-only
    STATUS      current
    DESCRIPTION
            "the value of interface's send power, in dbm format."
    ::= { slot6ModuleIfEntry 30 }

slot6ModuleifSpecific OBJECT-TYPE
    SYNTAX      OBJECT IDENTIFIER
    MAX-ACCESS  read-only
    STATUS      deprecated
    DESCRIPTION
            "A reference to MIB definitions specific to the particular
            media being used to realize the interface.  It is

            recommended that this value point to an instance of a MIB
            object in the media-specific MIB, i.e., that this object
            have the semantics associated with the InstancePointer
            textual convention defined in RFC 2579.  In fact, it is
            recommended that the media-specific MIB specify what value
            ifSpecific should/can take for values of ifType.  If no MIB
            definitions specific to the particular media are available,
            the value should be set to the OBJECT IDENTIFIER { 0 0 }."
    ::= { slot6ModuleIfEntry 31 }  
    
-- slot 7 --

-- slot7Table --

slot7Table OBJECT-TYPE
    SYNTAX      SEQUENCE OF Slot7Entry
    MAX-ACCESS  not-accessible
    STATUS      current
    DESCRIPTION
            "A list of all slot7Type's utilization."
    ::= { slot7 1 }  

slot7Entry OBJECT-TYPE
    SYNTAX      Slot7Entry
    MAX-ACCESS  not-accessible
    STATUS      current
    DESCRIPTION
            "An entry contains a slot7's utilization."
    INDEX   { slot7Index }
    ::= { slot7Table 1 }

Slot7Entry ::=
    SEQUENCE {     
		slot7Index                       Integer32,
		slot7Type                        DisplayString,
		slot7Status                      DisplayString,
		slot7Id                          Integer32
    }  

slot7Index OBJECT-TYPE
    SYNTAX      Integer32 (1..2147483647)
    MAX-ACCESS  not-accessible
    STATUS      current
    DESCRIPTION
            "A unique value, greater than zero, for each chassis`s slot7."
    ::= { slot7Entry 1 }

slot7Type OBJECT-TYPE
    SYNTAX      DisplayString (SIZE (0..255))
    MAX-ACCESS  read-only
    STATUS      current
    DESCRIPTION
            "the slot7Type of each chassis."
    ::= { slot7Entry 2 }

slot7Status OBJECT-TYPE
    SYNTAX      DisplayString (SIZE (0..255))
    MAX-ACCESS  read-only
    STATUS      current
    DESCRIPTION
            "A string to describe the board status." 
    ::= { slot7Entry 3 }   

slot7Id OBJECT-TYPE
    SYNTAX      Integer32
    MAX-ACCESS  read-only
    STATUS      current
    DESCRIPTION
            "slot id."
    ::= { slot7Entry 4 }

slot7Module OBJECT IDENTIFIER ::= { slot7 2 }

-- slot7ModuleTable --
slot7ModuleTable OBJECT-TYPE
    SYNTAX      SEQUENCE OF Slot7ModuleEntry
    MAX-ACCESS  not-accessible
    STATUS      current
    DESCRIPTION
            "A list of all slot7Module's utilization."
    ::= { slot7Module 1 }  

slot7ModuleEntry OBJECT-TYPE
    SYNTAX      Slot7ModuleEntry
    MAX-ACCESS  not-accessible
    STATUS      current
    DESCRIPTION
            "An entry contains a slot7Module's utilization."
    INDEX   { slot7ModuleIndex }
    ::= { slot7ModuleTable 1 }

Slot7ModuleEntry ::=
    SEQUENCE {     
		slot7ModuleIndex                       Integer32,
		slot7ModuleId                           DisplayString,  
		slot7ModuleIfNumber                     Integer32		
    } 

slot7ModuleIndex OBJECT-TYPE
    SYNTAX      Integer32 (1..2147483647)
    MAX-ACCESS  not-accessible
    STATUS      current
    DESCRIPTION
            "A unique value, greater than zero, for each chassis`s slot7."
    ::= { slot7ModuleEntry 1 }

slot7ModuleId OBJECT-TYPE
    SYNTAX      DisplayString (SIZE (0..32))
    MAX-ACCESS  read-only
    STATUS      current
    DESCRIPTION
            "the value of module`s id"
    ::= { slot7ModuleEntry 2 }
  
slot7ModuleIfNumber OBJECT-TYPE
    SYNTAX      Integer32(0..2147483647)
    MAX-ACCESS  read-only
    STATUS      current
    DESCRIPTION
            "The number of network interfaces (regardless of their
            current state) present on this system." 
    ::= { slot7ModuleEntry 3 } 
    
slot7ModuleIfTable OBJECT-TYPE
    SYNTAX      SEQUENCE OF Slot7ModuleIfEntry
    MAX-ACCESS  not-accessible
    STATUS      current
    DESCRIPTION
            "A list of interface entries.  The number of entries is
            given by the value of ifNumber."
    ::= { slot7Module 2 } 
    
slot7ModuleIfEntry OBJECT-TYPE
    SYNTAX      Slot7ModuleIfEntry
    MAX-ACCESS  not-accessible
    STATUS      current
    DESCRIPTION
            "An entry containing management information applicable to a
            particular interface."
    INDEX   { slot7ModuleifIndex }
    ::= { slot7ModuleIfTable 1 }
    
Slot7ModuleIfEntry ::=
    SEQUENCE {
        slot7ModuleifIndex                 InterfaceIndex,  
        slot7ModuleIfId                    DisplayString,  
        slot7ModuleifDescr                 DisplayString,           
        slot7ModuleifType                  IANAifType,   		
        slot7ModuleifMtu                   Integer32,                
        slot7ModuleifSpeed                 Counter64,               
        slot7ModuleifPhysAddress           PhysAddress,              
        slot7ModuleifAdminStatus           INTEGER,                  
        slot7ModuleifOperStatus            INTEGER,                  
        slot7ModuleifLastChange            TimeTicks,                
	slot7ModuleifInKbits   	           Counter64,
	slot7ModuleifOutKbits              Counter64,
        slot7ModuleifInOctets              Counter64,                
        slot7ModuleifInUcastPkts           Counter64,                
        slot7ModuleifInNUcastPkts          Counter64,    
        slot7ModuleifInDiscards            Counter64,
        slot7ModuleifInErrors              Counter64,
        slot7ModuleifInFcsErrorPkts        Counter64,
        slot7ModuleifInUnknownProtos       Counter64,	-- deprecated
        slot7ModuleifOutOctets             Counter64,
        slot7ModuleifOutUcastPkts          Counter64,
        slot7ModuleifOutNUcastPkts         Counter64,  -- deprecated
        slot7ModuleifOutDiscards           Counter64,
        slot7ModuleifOutErrors             Counter64,
        slot7ModuleifOutFcsErrorPkts       Counter64,
        slot7ModuleifOutQLen               Gauge32,    -- deprecated  
 	    slot7ModuleifInpps   	           Counter64,
	    slot7ModuleifOutpps              Counter64,       
        slot7ModuleifRxPower                DisplayString,
        slot7ModuleifTxPower                DisplayString,
        slot7ModuleifSpecific              OBJECT IDENTIFIER
    }         

slot7ModuleifIndex OBJECT-TYPE
    SYNTAX      InterfaceIndex
    MAX-ACCESS  read-only
    STATUS      current
    DESCRIPTION
            "A unique value, greater than zero, for each interface.  It
            is recommended that values are assigned contiguously
            starting from 1.  The value for each interface sub-layer
            must remain constant at least from one re-initialization of
            the entity's network management system to the next re-
            initialization."
    ::= { slot7ModuleIfEntry 1 }
    
slot7ModuleIfId OBJECT-TYPE
    SYNTAX      DisplayString (SIZE (0..32))
    MAX-ACCESS  read-only
    STATUS      current
    DESCRIPTION
            "the value of module`s id"
    ::= { slot7ModuleIfEntry 2 }
    
slot7ModuleifDescr OBJECT-TYPE
    SYNTAX      DisplayString (SIZE (0..255))
    MAX-ACCESS  read-only
    STATUS      current
    DESCRIPTION
            "A textual string containing information about the
            interface.  This string should include the name of the
            manufacturer, the product name and the version of the
            interface hardware/software."
    ::= { slot7ModuleIfEntry 3 }
    
slot7ModuleifType OBJECT-TYPE
    SYNTAX      IANAifType
    MAX-ACCESS  read-only
    STATUS      current
    DESCRIPTION
            "The type of interface.  Additional values for ifType are
            assigned by the Internet Assigned Numbers Authority (IANA),
            through updating the syntax of the IANAifType textual
            convention."
    ::= { slot7ModuleIfEntry 4 }

slot7ModuleifMtu OBJECT-TYPE
    SYNTAX      Integer32(1..2147483647)
    MAX-ACCESS  read-only
    STATUS      current
    DESCRIPTION
            "The size of the largest packet which can be sent/received
            on the interface, specified in octets.  For interfaces that
            are used for transmitting network datagrams, this is the
            size of the largest network datagram that can be sent on the
            interface."
    ::= { slot7ModuleIfEntry 5 }

slot7ModuleifSpeed OBJECT-TYPE
    SYNTAX      Counter64
    MAX-ACCESS  read-only
    STATUS      current
    DESCRIPTION
            "An estimate of the interface's current bandwidth in bits
            per second.  For interfaces which do not vary in bandwidth
            or for those where no accurate estimation can be made, this
            object should contain the nominal bandwidth. For a sub-layer
            which has no concept of bandwidth, this object should be zero."
    ::= { slot7ModuleIfEntry 6 }

slot7ModuleifPhysAddress OBJECT-TYPE
    SYNTAX      PhysAddress
    MAX-ACCESS  read-only
    STATUS      current
    DESCRIPTION
            "The interface's address at its protocol sub-layer.  For
            example, for an 802.x interface, this object normally
            contains a MAC address.  The interface's media-specific MIB
            must define the bit and byte ordering and the format of the
            value of this object.  For interfaces which do not have such
            an address (e.g., a serial line), this object should contain
            an octet string of zero length."
    ::= { slot7ModuleIfEntry 7 }
    
slot7ModuleifAdminStatus OBJECT-TYPE
    SYNTAX  INTEGER {
                up(1),       -- ready to pass packets
                down(2),
                testing(3)   -- in some test mode
            }
    MAX-ACCESS  read-write
    STATUS      current
    DESCRIPTION
            "The desired state of the interface.  The testing(3) state
            indicates that no operational packets can be passed.  When a
            managed system initializes, all interfaces start with
            ifAdminStatus in the down(2) state.  As a result of either
            explicit management action or per configuration information
            retained by the managed system, ifAdminStatus is then
            changed to either the up(1) or testing(3) states (or remains
            in the down(2) state)."
    ::= { slot7ModuleIfEntry 8 }

slot7ModuleifOperStatus OBJECT-TYPE
    SYNTAX  INTEGER {
                up(1),        -- ready to pass packets
                down(2),
                testing(3),   -- in some test mode
                unknown(4),   -- status can not be determined
                              -- for some reason.
                dormant(5),
                notPresent(6),    -- some component is missing
                lowerLayerDown(7) -- down due to state of
                                  -- lower-layer interface(s)
            }
    MAX-ACCESS  read-only
    STATUS      current
    DESCRIPTION
            "The current operational state of the interface.  The
            testing(3) state indicates that no operational packets can
            be passed.  If ifAdminStatus is down(2) then ifOperStatus
            should be down(2).  If ifAdminStatus is changed to up(1)
            then ifOperStatus should change to up(1) if the interface is
            ready to transmit and receive network traffic; it should
            change to dormant(5) if the interface is waiting for
            external actions (such as a serial line waiting for an
            incoming connection); it should remain in the down(2) state
            if and only if there is a fault that prevents it from going
            to the up(1) state; it should remain in the notPresent(6)
            state if the interface has missing (typically, hardware)
            components."
    ::= { slot7ModuleIfEntry 9 }

slot7ModuleifLastChange OBJECT-TYPE
    SYNTAX      TimeTicks
    MAX-ACCESS  read-only
    STATUS      current
    DESCRIPTION
            "The value of sysUpTime at the time the interface entered
            its current operational state.  If the current state was
            entered prior to the last re-initialization of the local
            network management subsystem, then this object contains a
            zero value."
    ::= { slot7ModuleIfEntry 10 }

slot7ModuleifInKbits OBJECT-TYPE
    SYNTAX      Counter64
    MAX-ACCESS  read-only
    STATUS      current
    DESCRIPTION
            "The real time rate received on the interface, in Kbits
	    format.

            Discontinuities in the value of this counter can occur at
            re-initialization of the management system, and at other
            times as indicated by the value of
            ifCounterDiscontinuityTime."
    ::= { slot7ModuleIfEntry 11 }

slot7ModuleifOutKbits OBJECT-TYPE
    SYNTAX      Counter64
    MAX-ACCESS  read-only
    STATUS      current
    DESCRIPTION
            "The real time rate send on the interface, in Kbits
	    format.

            Discontinuities in the value of this counter can occur at
            re-initialization of the management system, and at other
            times as indicated by the value of
            ifCounterDiscontinuityTime."
    ::= { slot7ModuleIfEntry 12 }

slot7ModuleifInOctets OBJECT-TYPE
    SYNTAX      Counter64
    MAX-ACCESS  read-only
    STATUS      current
    DESCRIPTION
            "The total number of octets received on the interface,
            including framing characters.

            Discontinuities in the value of this counter can occur at
            re-initialization of the management system, and at other
            times as indicated by the value of
            ifCounterDiscontinuityTime."
    ::= { slot7ModuleIfEntry 13 }

slot7ModuleifInUcastPkts OBJECT-TYPE
    SYNTAX      Counter64
    MAX-ACCESS  read-only
    STATUS      current
    DESCRIPTION
            "The number of packets, delivered by this sub-layer to a
            higher (sub-)layer, which were not addressed to a multicast
            or broadcast address at this sub-layer.

            Discontinuities in the value of this counter can occur at
            re-initialization of the management system, and at other
            times as indicated by the value of
            ifCounterDiscontinuityTime."
    ::= { slot7ModuleIfEntry 14 }

slot7ModuleifInNUcastPkts OBJECT-TYPE
    SYNTAX  Counter64
    MAX-ACCESS  read-only
    STATUS      current
    DESCRIPTION
            "The number of packets, delivered by this sub-layer to a
            higher (sub-)layer, which were addressed to a multicast or
            broadcast address at this sub-layer.

            Discontinuities in the value of this counter can occur at
            re-initialization of the management system, and at other
            times as indicated by the value of
            ifCounterDiscontinuityTime.

            This object is deprecated in favour of ifInMulticastPkts and
            ifInBroadcastPkts."
    ::= { slot7ModuleIfEntry 15 }

slot7ModuleifInDiscards OBJECT-TYPE
    SYNTAX      Counter64
    MAX-ACCESS  read-only
    STATUS      current
    DESCRIPTION
            "The number of inbound packets which were chosen to be
            discarded even though no errors had been detected to prevent

            their being deliverable to a higher-layer protocol.  One
            possible reason for discarding such a packet could be to
            free up buffer space.

            Discontinuities in the value of this counter can occur at
            re-initialization of the management system, and at other
            times as indicated by the value of
            ifCounterDiscontinuityTime."
    ::= { slot7ModuleIfEntry 16 }

slot7ModuleifInErrors OBJECT-TYPE
    SYNTAX      Counter64
    MAX-ACCESS  read-only
    STATUS      current
    DESCRIPTION
            "For packet-oriented interfaces, the number of inbound
            packets that contained errors preventing them from being
            deliverable to a higher-layer protocol.  For character-
            oriented or fixed-length interfaces, the number of inbound
            transmission units that contained errors preventing them
            from being deliverable to a higher-layer protocol.

            Discontinuities in the value of this counter can occur at
            re-initialization of the management system, and at other
            times as indicated by the value of
            ifCounterDiscontinuityTime."
    ::= { slot7ModuleIfEntry 17 }

slot7ModuleifInFcsErrorPkts OBJECT-TYPE
    SYNTAX      Counter64
    MAX-ACCESS  read-only
    STATUS      current
    DESCRIPTION
            "FCS error pakets."
    ::= { slot7ModuleIfEntry 18 }

slot7ModuleifInUnknownProtos OBJECT-TYPE
    SYNTAX      Counter64
    MAX-ACCESS  read-only
    STATUS      current
    DESCRIPTION
            "For packet-oriented interfaces, the number of packets
            received via the interface which were discarded because of
            an unknown or unsupported protocol.  For character-oriented
            or fixed-length interfaces that support protocol
            multiplexing the number of transmission units received via
            the interface which were discarded because of an unknown or
            unsupported protocol.  For any interface that does not
            support protocol multiplexing, this counter will always be
            0.

            Discontinuities in the value of this counter can occur at
            re-initialization of the management system, and at other
            times as indicated by the value of
            ifCounterDiscontinuityTime."
    ::= { slot7ModuleIfEntry 19 }

slot7ModuleifOutOctets OBJECT-TYPE
    SYNTAX      Counter64
    MAX-ACCESS  read-only
    STATUS      current
    DESCRIPTION
            "The total number of octets transmitted out of the
            interface, including framing characters.

            Discontinuities in the value of this counter can occur at
            re-initialization of the management system, and at other
            times as indicated by the value of
            ifCounterDiscontinuityTime."
    ::= { slot7ModuleIfEntry 20 }

slot7ModuleifOutUcastPkts OBJECT-TYPE
    SYNTAX      Counter64
    MAX-ACCESS  read-only
    STATUS      current
    DESCRIPTION
            "The total number of packets that higher-level protocols
            requested be transmitted, and which were not addressed to a
            multicast or broadcast address at this sub-layer, including
            those that were discarded or not sent.

            Discontinuities in the value of this counter can occur at
            re-initialization of the management system, and at other
            times as indicated by the value of
            ifCounterDiscontinuityTime."
    ::= { slot7ModuleIfEntry 21 }

slot7ModuleifOutNUcastPkts OBJECT-TYPE
    SYNTAX      Counter64
    MAX-ACCESS  read-only
    STATUS      deprecated
    DESCRIPTION
            "The total number of packets that higher-level protocols
            requested be transmitted, and which were addressed to a
            multicast or broadcast address at this sub-layer, including
            those that were discarded or not sent.

            Discontinuities in the value of this counter can occur at
            re-initialization of the management system, and at other
            times as indicated by the value of
            ifCounterDiscontinuityTime.

            This object is deprecated in favour of ifOutMulticastPkts
            and ifOutBroadcastPkts."
    ::= { slot7ModuleIfEntry 22 }

slot7ModuleifOutDiscards OBJECT-TYPE
    SYNTAX      Counter64
    MAX-ACCESS  read-only
    STATUS      current
    DESCRIPTION
            "The number of outbound packets which were chosen to be
            discarded even though no errors had been detected to prevent
            their being transmitted.  One possible reason for discarding
            such a packet could be to free up buffer space.

            Discontinuities in the value of this counter can occur at
            re-initialization of the management system, and at other
            times as indicated by the value of
            ifCounterDiscontinuityTime."
    ::= { slot7ModuleIfEntry 23 }

slot7ModuleifOutErrors OBJECT-TYPE
    SYNTAX      Counter64
    MAX-ACCESS  read-only
    STATUS      current
    DESCRIPTION
            "For packet-oriented interfaces, the number of outbound
            packets that could not be transmitted because of errors.
            For character-oriented or fixed-length interfaces, the
            number of outbound transmission units that could not be
            transmitted because of errors.

            Discontinuities in the value of this counter can occur at
            re-initialization of the management system, and at other
            times as indicated by the value of
            ifCounterDiscontinuityTime."
    ::= { slot7ModuleIfEntry 24 }

slot7ModuleifOutFcsErrorPkts OBJECT-TYPE
    SYNTAX      Counter64
    MAX-ACCESS  read-only
    STATUS      current
    DESCRIPTION
            "FCS error pakets."
    ::= { slot7ModuleIfEntry 25 }

slot7ModuleifOutQLen OBJECT-TYPE
    SYNTAX      Gauge32
    MAX-ACCESS  read-only
    STATUS      deprecated
    DESCRIPTION
            "The length of the output packet queue (in packets)."
    ::= { slot7ModuleIfEntry 26 }

slot7ModuleifInpps OBJECT-TYPE
    SYNTAX      Counter64
    MAX-ACCESS  read-only
    STATUS      current
    DESCRIPTION
            "The real time rate received on the interface, in pps
	    format.

            Discontinuities in the value of this counter can occur at
            re-initialization of the management system, and at other
            times as indicated by the value of
            ifCounterDiscontinuityTime."
    ::= { slot7ModuleIfEntry 27 }

slot7ModuleifOutpps OBJECT-TYPE
    SYNTAX      Counter64
    MAX-ACCESS  read-only
    STATUS      current
    DESCRIPTION
            "The real time rate send on the interface, in pps
	    format.

            Discontinuities in the value of this counter can occur at
            re-initialization of the management system, and at other
            times as indicated by the value of
            ifCounterDiscontinuityTime."
    ::= { slot7ModuleIfEntry 28 }
    
slot7ModuleifRxPower OBJECT-TYPE
    SYNTAX      DisplayString (SIZE (0..255))
    MAX-ACCESS  read-only
    STATUS      current
    DESCRIPTION
            "the value of interface's received power, in dbm format."
    ::= { slot7ModuleIfEntry 29 }
    
slot7ModuleifTxPower OBJECT-TYPE
    SYNTAX      DisplayString (SIZE (0..255))
    MAX-ACCESS  read-only
    STATUS      current
    DESCRIPTION
            "the value of interface's send power, in dbm format."
    ::= { slot7ModuleIfEntry 30 }

slot7ModuleifSpecific OBJECT-TYPE
    SYNTAX      OBJECT IDENTIFIER
    MAX-ACCESS  read-only
    STATUS      deprecated
    DESCRIPTION
            "A reference to MIB definitions specific to the particular
            media being used to realize the interface.  It is

            recommended that this value point to an instance of a MIB
            object in the media-specific MIB, i.e., that this object
            have the semantics associated with the InstancePointer
            textual convention defined in RFC 2579.  In fact, it is
            recommended that the media-specific MIB specify what value
            ifSpecific should/can take for values of ifType.  If no MIB
            definitions specific to the particular media are available,
            the value should be set to the OBJECT IDENTIFIER { 0 0 }."
    ::= { slot7ModuleIfEntry 31 }  
    
-- slot 8 --

-- slot8Table --

slot8Table OBJECT-TYPE
    SYNTAX      SEQUENCE OF Slot8Entry
    MAX-ACCESS  not-accessible
    STATUS      current
    DESCRIPTION
            "A list of all slot8Type's utilization."
    ::= { slot8 1 }  

slot8Entry OBJECT-TYPE
    SYNTAX      Slot8Entry
    MAX-ACCESS  not-accessible
    STATUS      current
    DESCRIPTION
            "An entry contains a slot8's utilization."
    INDEX   { slot8Index }
    ::= { slot8Table 1 }

Slot8Entry ::=
    SEQUENCE {     
		slot8Index                       Integer32,
		slot8Type                        DisplayString,
		slot8Status                      DisplayString,
		slot8Id                          Integer32
    }  

slot8Index OBJECT-TYPE
    SYNTAX      Integer32 (1..2147483647)
    MAX-ACCESS  not-accessible
    STATUS      current
    DESCRIPTION
            "A unique value, greater than zero, for each chassis`s slot8."
    ::= { slot8Entry 1 }

slot8Type OBJECT-TYPE
    SYNTAX      DisplayString (SIZE (0..255))
    MAX-ACCESS  read-only
    STATUS      current
    DESCRIPTION
            "the slot8Type of each chassis."
    ::= { slot8Entry 2 }

slot8Status OBJECT-TYPE
    SYNTAX      DisplayString (SIZE (0..255))
    MAX-ACCESS  read-only
    STATUS      current
    DESCRIPTION
            "A string to describe the board status." 
    ::= { slot8Entry 3 }   

slot8Id OBJECT-TYPE
    SYNTAX      Integer32
    MAX-ACCESS  read-only
    STATUS      current
    DESCRIPTION
            "slot id."
    ::= { slot8Entry 4 }

slot8Module OBJECT IDENTIFIER ::= { slot8 2 }

-- slot8ModuleTable --
slot8ModuleTable OBJECT-TYPE
    SYNTAX      SEQUENCE OF Slot8ModuleEntry
    MAX-ACCESS  not-accessible
    STATUS      current
    DESCRIPTION
            "A list of all slot8Module's utilization."
    ::= { slot8Module 1 }  

slot8ModuleEntry OBJECT-TYPE
    SYNTAX      Slot8ModuleEntry
    MAX-ACCESS  not-accessible
    STATUS      current
    DESCRIPTION
            "An entry contains a slot8Module's utilization."
    INDEX   { slot8ModuleIndex }
    ::= { slot8ModuleTable 1 }

Slot8ModuleEntry ::=
    SEQUENCE {     
		slot8ModuleIndex                       Integer32,
		slot8ModuleId                           DisplayString,  
		slot8ModuleIfNumber                     Integer32		
    } 

slot8ModuleIndex OBJECT-TYPE
    SYNTAX      Integer32 (1..2147483647)
    MAX-ACCESS  not-accessible
    STATUS      current
    DESCRIPTION
            "A unique value, greater than zero, for each chassis`s slot8."
    ::= { slot8ModuleEntry 1 }

slot8ModuleId OBJECT-TYPE
    SYNTAX      DisplayString (SIZE (0..32))
    MAX-ACCESS  read-only
    STATUS      current
    DESCRIPTION
            "the value of module`s id"
    ::= { slot8ModuleEntry 2 }
  
slot8ModuleIfNumber OBJECT-TYPE
    SYNTAX      Integer32(0..2147483647)
    MAX-ACCESS  read-only
    STATUS      current
    DESCRIPTION
            "The number of network interfaces (regardless of their
            current state) present on this system." 
    ::= { slot8ModuleEntry 3 } 
    
slot8ModuleIfTable OBJECT-TYPE
    SYNTAX      SEQUENCE OF Slot8ModuleIfEntry
    MAX-ACCESS  not-accessible
    STATUS      current
    DESCRIPTION
            "A list of interface entries.  The number of entries is
            given by the value of ifNumber."
    ::= { slot8Module 2 } 
    
slot8ModuleIfEntry OBJECT-TYPE
    SYNTAX      Slot8ModuleIfEntry
    MAX-ACCESS  not-accessible
    STATUS      current
    DESCRIPTION
            "An entry containing management information applicable to a
            particular interface."
    INDEX   { slot8ModuleifIndex }
    ::= { slot8ModuleIfTable 1 }
    
Slot8ModuleIfEntry ::=
    SEQUENCE {
        slot8ModuleifIndex                 InterfaceIndex,  
        slot8ModuleIfId                    DisplayString,  
        slot8ModuleifDescr                 DisplayString,           
        slot8ModuleifType                  IANAifType,   		
        slot8ModuleifMtu                   Integer32,                
        slot8ModuleifSpeed                 Counter64,               
        slot8ModuleifPhysAddress           PhysAddress,              
        slot8ModuleifAdminStatus           INTEGER,                  
        slot8ModuleifOperStatus            INTEGER,                  
        slot8ModuleifLastChange            TimeTicks,                
	slot8ModuleifInKbits   	           Counter64,
	slot8ModuleifOutKbits              Counter64,
        slot8ModuleifInOctets              Counter64,                
        slot8ModuleifInUcastPkts           Counter64,                
        slot8ModuleifInNUcastPkts          Counter64,  
        slot8ModuleifInDiscards            Counter64,
        slot8ModuleifInErrors              Counter64,
        slot8ModuleifInFcsErrorPkts        Counter64,
        slot8ModuleifInUnknownProtos       Counter64,	-- deprecated
        slot8ModuleifOutOctets             Counter64,
        slot8ModuleifOutUcastPkts          Counter64,
        slot8ModuleifOutNUcastPkts         Counter64,  -- deprecated
        slot8ModuleifOutDiscards           Counter64,
        slot8ModuleifOutErrors             Counter64,
        slot8ModuleifOutFcsErrorPkts       Counter64,
        slot8ModuleifOutQLen               Gauge32,    -- deprecated  
	    slot8ModuleifInpps   	           Counter64,
	    slot8ModuleifOutpps              Counter64,        
        slot8ModuleifRxPower                DisplayString,
        slot8ModuleifTxPower                DisplayString,
        slot8ModuleifSpecific              OBJECT IDENTIFIER
    }         

slot8ModuleifIndex OBJECT-TYPE
    SYNTAX      InterfaceIndex
    MAX-ACCESS  read-only
    STATUS      current
    DESCRIPTION
            "A unique value, greater than zero, for each interface.  It
            is recommended that values are assigned contiguously
            starting from 1.  The value for each interface sub-layer
            must remain constant at least from one re-initialization of
            the entity's network management system to the next re-
            initialization."
    ::= { slot8ModuleIfEntry 1 }
    
slot8ModuleIfId OBJECT-TYPE
    SYNTAX      DisplayString (SIZE (0..32))
    MAX-ACCESS  read-only
    STATUS      current
    DESCRIPTION
            "the value of module`s id"
    ::= { slot8ModuleIfEntry 2 }
    
slot8ModuleifDescr OBJECT-TYPE
    SYNTAX      DisplayString (SIZE (0..255))
    MAX-ACCESS  read-only
    STATUS      current
    DESCRIPTION
            "A textual string containing information about the
            interface.  This string should include the name of the
            manufacturer, the product name and the version of the
            interface hardware/software."
    ::= { slot8ModuleIfEntry 3 }
    
slot8ModuleifType OBJECT-TYPE
    SYNTAX      IANAifType
    MAX-ACCESS  read-only
    STATUS      current
    DESCRIPTION
            "The type of interface.  Additional values for ifType are
            assigned by the Internet Assigned Numbers Authority (IANA),
            through updating the syntax of the IANAifType textual
            convention."
    ::= { slot8ModuleIfEntry 4 }

slot8ModuleifMtu OBJECT-TYPE
    SYNTAX      Integer32(1..2147483647)
    MAX-ACCESS  read-only
    STATUS      current
    DESCRIPTION
            "The size of the largest packet which can be sent/received
            on the interface, specified in octets.  For interfaces that
            are used for transmitting network datagrams, this is the
            size of the largest network datagram that can be sent on the
            interface."
    ::= { slot8ModuleIfEntry 5 }

slot8ModuleifSpeed OBJECT-TYPE
    SYNTAX      Counter64
    MAX-ACCESS  read-only
    STATUS      current
    DESCRIPTION
            "An estimate of the interface's current bandwidth in bits
            per second.  For interfaces which do not vary in bandwidth
            or for those where no accurate estimation can be made, this
            object should contain the nominal bandwidth. For a sub-layer
            which has no concept of bandwidth, this object should be zero."
    ::= { slot8ModuleIfEntry 6 }

slot8ModuleifPhysAddress OBJECT-TYPE
    SYNTAX      PhysAddress
    MAX-ACCESS  read-only
    STATUS      current
    DESCRIPTION
            "The interface's address at its protocol sub-layer.  For
            example, for an 802.x interface, this object normally
            contains a MAC address.  The interface's media-specific MIB
            must define the bit and byte ordering and the format of the
            value of this object.  For interfaces which do not have such
            an address (e.g., a serial line), this object should contain
            an octet string of zero length."
    ::= { slot8ModuleIfEntry 7 }
    
slot8ModuleifAdminStatus OBJECT-TYPE
    SYNTAX  INTEGER {
                up(1),       -- ready to pass packets
                down(2),
                testing(3)   -- in some test mode
            }
    MAX-ACCESS  read-write
    STATUS      current
    DESCRIPTION
            "The desired state of the interface.  The testing(3) state
            indicates that no operational packets can be passed.  When a
            managed system initializes, all interfaces start with
            ifAdminStatus in the down(2) state.  As a result of either
            explicit management action or per configuration information
            retained by the managed system, ifAdminStatus is then
            changed to either the up(1) or testing(3) states (or remains
            in the down(2) state)."
    ::= { slot8ModuleIfEntry 8 }

slot8ModuleifOperStatus OBJECT-TYPE
    SYNTAX  INTEGER {
                up(1),        -- ready to pass packets
                down(2),
                testing(3),   -- in some test mode
                unknown(4),   -- status can not be determined
                              -- for some reason.
                dormant(5),
                notPresent(6),    -- some component is missing
                lowerLayerDown(7) -- down due to state of
                                  -- lower-layer interface(s)
            }
    MAX-ACCESS  read-only
    STATUS      current
    DESCRIPTION
            "The current operational state of the interface.  The
            testing(3) state indicates that no operational packets can
            be passed.  If ifAdminStatus is down(2) then ifOperStatus
            should be down(2).  If ifAdminStatus is changed to up(1)
            then ifOperStatus should change to up(1) if the interface is
            ready to transmit and receive network traffic; it should
            change to dormant(5) if the interface is waiting for
            external actions (such as a serial line waiting for an
            incoming connection); it should remain in the down(2) state
            if and only if there is a fault that prevents it from going
            to the up(1) state; it should remain in the notPresent(6)
            state if the interface has missing (typically, hardware)
            components."
    ::= { slot8ModuleIfEntry 9 }

slot8ModuleifLastChange OBJECT-TYPE
    SYNTAX      TimeTicks
    MAX-ACCESS  read-only
    STATUS      current
    DESCRIPTION
            "The value of sysUpTime at the time the interface entered
            its current operational state.  If the current state was
            entered prior to the last re-initialization of the local
            network management subsystem, then this object contains a
            zero value."
    ::= { slot8ModuleIfEntry 10 }

slot8ModuleifInKbits OBJECT-TYPE
    SYNTAX      Counter64
    MAX-ACCESS  read-only
    STATUS      current
    DESCRIPTION
            "The real time rate received on the interface, in Kbits
	    format.

            Discontinuities in the value of this counter can occur at
            re-initialization of the management system, and at other
            times as indicated by the value of
            ifCounterDiscontinuityTime."
    ::= { slot8ModuleIfEntry 11 }

slot8ModuleifOutKbits OBJECT-TYPE
    SYNTAX      Counter64
    MAX-ACCESS  read-only
    STATUS      current
    DESCRIPTION
            "The real time rate send on the interface, in Kbits
	    format.

            Discontinuities in the value of this counter can occur at
            re-initialization of the management system, and at other
            times as indicated by the value of
            ifCounterDiscontinuityTime."
    ::= { slot8ModuleIfEntry 12 }

slot8ModuleifInOctets OBJECT-TYPE
    SYNTAX      Counter64
    MAX-ACCESS  read-only
    STATUS      current
    DESCRIPTION
            "The total number of octets received on the interface,
            including framing characters.

            Discontinuities in the value of this counter can occur at
            re-initialization of the management system, and at other
            times as indicated by the value of
            ifCounterDiscontinuityTime."
    ::= { slot8ModuleIfEntry 13 }

slot8ModuleifInUcastPkts OBJECT-TYPE
    SYNTAX      Counter64
    MAX-ACCESS  read-only
    STATUS      current
    DESCRIPTION
            "The number of packets, delivered by this sub-layer to a
            higher (sub-)layer, which were not addressed to a multicast
            or broadcast address at this sub-layer.

            Discontinuities in the value of this counter can occur at
            re-initialization of the management system, and at other
            times as indicated by the value of
            ifCounterDiscontinuityTime."
    ::= { slot8ModuleIfEntry 14 }

slot8ModuleifInNUcastPkts OBJECT-TYPE
    SYNTAX  Counter64
    MAX-ACCESS  read-only
    STATUS      current
    DESCRIPTION
            "The number of packets, delivered by this sub-layer to a
            higher (sub-)layer, which were addressed to a multicast or
            broadcast address at this sub-layer.

            Discontinuities in the value of this counter can occur at
            re-initialization of the management system, and at other
            times as indicated by the value of
            ifCounterDiscontinuityTime.

            This object is deprecated in favour of ifInMulticastPkts and
            ifInBroadcastPkts."
    ::= { slot8ModuleIfEntry 15 }

slot8ModuleifInDiscards OBJECT-TYPE
    SYNTAX      Counter64
    MAX-ACCESS  read-only
    STATUS      current
    DESCRIPTION
            "The number of inbound packets which were chosen to be
            discarded even though no errors had been detected to prevent

            their being deliverable to a higher-layer protocol.  One
            possible reason for discarding such a packet could be to
            free up buffer space.

            Discontinuities in the value of this counter can occur at
            re-initialization of the management system, and at other
            times as indicated by the value of
            ifCounterDiscontinuityTime."
    ::= { slot8ModuleIfEntry 16 }

slot8ModuleifInErrors OBJECT-TYPE
    SYNTAX      Counter64
    MAX-ACCESS  read-only
    STATUS      current
    DESCRIPTION
            "For packet-oriented interfaces, the number of inbound
            packets that contained errors preventing them from being
            deliverable to a higher-layer protocol.  For character-
            oriented or fixed-length interfaces, the number of inbound
            transmission units that contained errors preventing them
            from being deliverable to a higher-layer protocol.

            Discontinuities in the value of this counter can occur at
            re-initialization of the management system, and at other
            times as indicated by the value of
            ifCounterDiscontinuityTime."
    ::= { slot8ModuleIfEntry 17 }

slot8ModuleifInFcsErrorPkts OBJECT-TYPE
    SYNTAX      Counter64
    MAX-ACCESS  read-only
    STATUS      current
    DESCRIPTION
            "FCS error pakets."
    ::= { slot8ModuleIfEntry 18 }

slot8ModuleifInUnknownProtos OBJECT-TYPE
    SYNTAX      Counter64
    MAX-ACCESS  read-only
    STATUS      current
    DESCRIPTION
            "For packet-oriented interfaces, the number of packets
            received via the interface which were discarded because of
            an unknown or unsupported protocol.  For character-oriented
            or fixed-length interfaces that support protocol
            multiplexing the number of transmission units received via
            the interface which were discarded because of an unknown or
            unsupported protocol.  For any interface that does not
            support protocol multiplexing, this counter will always be
            0.

            Discontinuities in the value of this counter can occur at
            re-initialization of the management system, and at other
            times as indicated by the value of
            ifCounterDiscontinuityTime."
    ::= { slot8ModuleIfEntry 19 }

slot8ModuleifOutOctets OBJECT-TYPE
    SYNTAX      Counter64
    MAX-ACCESS  read-only
    STATUS      current
    DESCRIPTION
            "The total number of octets transmitted out of the
            interface, including framing characters.

            Discontinuities in the value of this counter can occur at
            re-initialization of the management system, and at other
            times as indicated by the value of
            ifCounterDiscontinuityTime."
    ::= { slot8ModuleIfEntry 20 }

slot8ModuleifOutUcastPkts OBJECT-TYPE
    SYNTAX      Counter64
    MAX-ACCESS  read-only
    STATUS      current
    DESCRIPTION
            "The total number of packets that higher-level protocols
            requested be transmitted, and which were not addressed to a
            multicast or broadcast address at this sub-layer, including
            those that were discarded or not sent.

            Discontinuities in the value of this counter can occur at
            re-initialization of the management system, and at other
            times as indicated by the value of
            ifCounterDiscontinuityTime."
    ::= { slot8ModuleIfEntry 21 }

slot8ModuleifOutNUcastPkts OBJECT-TYPE
    SYNTAX      Counter64
    MAX-ACCESS  read-only
    STATUS      deprecated
    DESCRIPTION
            "The total number of packets that higher-level protocols
            requested be transmitted, and which were addressed to a
            multicast or broadcast address at this sub-layer, including
            those that were discarded or not sent.

            Discontinuities in the value of this counter can occur at
            re-initialization of the management system, and at other
            times as indicated by the value of
            ifCounterDiscontinuityTime.

            This object is deprecated in favour of ifOutMulticastPkts
            and ifOutBroadcastPkts."
    ::= { slot8ModuleIfEntry 22 }

slot8ModuleifOutDiscards OBJECT-TYPE
    SYNTAX      Counter64
    MAX-ACCESS  read-only
    STATUS      current
    DESCRIPTION
            "The number of outbound packets which were chosen to be
            discarded even though no errors had been detected to prevent
            their being transmitted.  One possible reason for discarding
            such a packet could be to free up buffer space.

            Discontinuities in the value of this counter can occur at
            re-initialization of the management system, and at other
            times as indicated by the value of
            ifCounterDiscontinuityTime."
    ::= { slot8ModuleIfEntry 23 }

slot8ModuleifOutErrors OBJECT-TYPE
    SYNTAX      Counter64
    MAX-ACCESS  read-only
    STATUS      current
    DESCRIPTION
            "For packet-oriented interfaces, the number of outbound
            packets that could not be transmitted because of errors.
            For character-oriented or fixed-length interfaces, the
            number of outbound transmission units that could not be
            transmitted because of errors.

            Discontinuities in the value of this counter can occur at
            re-initialization of the management system, and at other
            times as indicated by the value of
            ifCounterDiscontinuityTime."
    ::= { slot8ModuleIfEntry 24 }

slot8ModuleifOutFcsErrorPkts OBJECT-TYPE
    SYNTAX      Counter64
    MAX-ACCESS  read-only
    STATUS      current
    DESCRIPTION
            "FCS error pakets."
    ::= { slot8ModuleIfEntry 25 }

slot8ModuleifOutQLen OBJECT-TYPE
    SYNTAX      Gauge32
    MAX-ACCESS  read-only
    STATUS      deprecated
    DESCRIPTION
            "The length of the output packet queue (in packets)."
    ::= { slot8ModuleIfEntry 26 }

slot8ModuleifInpps OBJECT-TYPE
    SYNTAX      Counter64
    MAX-ACCESS  read-only
    STATUS      current
    DESCRIPTION
            "The real time rate received on the interface, in pps
	    format.

            Discontinuities in the value of this counter can occur at
            re-initialization of the management system, and at other
            times as indicated by the value of
            ifCounterDiscontinuityTime."
    ::= { slot8ModuleIfEntry 27 }

slot8ModuleifOutpps OBJECT-TYPE
    SYNTAX      Counter64
    MAX-ACCESS  read-only
    STATUS      current
    DESCRIPTION
            "The real time rate send on the interface, in pps
	    format.

            Discontinuities in the value of this counter can occur at
            re-initialization of the management system, and at other
            times as indicated by the value of
            ifCounterDiscontinuityTime."
    ::= { slot8ModuleIfEntry 28 }
    
slot8ModuleifRxPower OBJECT-TYPE
    SYNTAX      DisplayString (SIZE (0..255))
    MAX-ACCESS  read-only
    STATUS      current
    DESCRIPTION
            "the value of interface's received power, in dbm format."
    ::= { slot8ModuleIfEntry 29 }
    
slot8ModuleifTxPower OBJECT-TYPE
    SYNTAX      DisplayString (SIZE (0..255))
    MAX-ACCESS  read-only
    STATUS      current
    DESCRIPTION
            "the value of interface's send power, in dbm format."
    ::= { slot8ModuleIfEntry 30 }

slot8ModuleifSpecific OBJECT-TYPE
    SYNTAX      OBJECT IDENTIFIER
    MAX-ACCESS  read-only
    STATUS      deprecated
    DESCRIPTION
            "A reference to MIB definitions specific to the particular
            media being used to realize the interface.  It is

            recommended that this value point to an instance of a MIB
            object in the media-specific MIB, i.e., that this object
            have the semantics associated with the InstancePointer
            textual convention defined in RFC 2579.  In fact, it is
            recommended that the media-specific MIB specify what value
            ifSpecific should/can take for values of ifType.  If no MIB
            definitions specific to the particular media are available,
            the value should be set to the OBJECT IDENTIFIER { 0 0 }."
    ::= { slot8ModuleIfEntry 31 }  
    
-- slot 9 --

-- slot9Table --

slot9Table OBJECT-TYPE
    SYNTAX      SEQUENCE OF Slot9Entry
    MAX-ACCESS  not-accessible
    STATUS      current
    DESCRIPTION
            "A list of all slot9Type's utilization."
    ::= { slot9 1 }  

slot9Entry OBJECT-TYPE
    SYNTAX      Slot9Entry
    MAX-ACCESS  not-accessible
    STATUS      current
    DESCRIPTION
            "An entry contains a slot9's utilization."
    INDEX   { slot9Index }
    ::= { slot9Table 1 }

Slot9Entry ::=
    SEQUENCE {     
		slot9Index                       Integer32,
		slot9Type                        DisplayString,
		slot9Status                      DisplayString,
		slot9Id                          Integer32
    }  

slot9Index OBJECT-TYPE
    SYNTAX      Integer32 (1..2147483647)
    MAX-ACCESS  not-accessible
    STATUS      current
    DESCRIPTION
            "A unique value, greater than zero, for each chassis`s slot9."
    ::= { slot9Entry 1 }

slot9Type OBJECT-TYPE
    SYNTAX      DisplayString (SIZE (0..255))
    MAX-ACCESS  read-only
    STATUS      current
    DESCRIPTION
            "the slot9Type of each chassis."
    ::= { slot9Entry 2 }

slot9Status OBJECT-TYPE
    SYNTAX      DisplayString (SIZE (0..255))
    MAX-ACCESS  read-only
    STATUS      current
    DESCRIPTION
            "A string to describe the board status." 
    ::= { slot9Entry 3 }   

slot9Id OBJECT-TYPE
    SYNTAX      Integer32
    MAX-ACCESS  read-only
    STATUS      current
    DESCRIPTION
            "slot id."
    ::= { slot9Entry 4 }

slot9Module OBJECT IDENTIFIER ::= { slot9 2 }

-- slot9ModuleTable --
slot9ModuleTable OBJECT-TYPE
    SYNTAX      SEQUENCE OF Slot9ModuleEntry
    MAX-ACCESS  not-accessible
    STATUS      current
    DESCRIPTION
            "A list of all slot9Module's utilization."
    ::= { slot9Module 1 }  

slot9ModuleEntry OBJECT-TYPE
    SYNTAX      Slot9ModuleEntry
    MAX-ACCESS  not-accessible
    STATUS      current
    DESCRIPTION
            "An entry contains a slot9Module's utilization."
    INDEX   { slot9ModuleIndex }
    ::= { slot9ModuleTable 1 }

Slot9ModuleEntry ::=
    SEQUENCE {     
		slot9ModuleIndex                       Integer32,
		slot9ModuleId                           DisplayString,  
		slot9ModuleIfNumber                     Integer32		
    } 

slot9ModuleIndex OBJECT-TYPE
    SYNTAX      Integer32 (1..2147483647)
    MAX-ACCESS  not-accessible
    STATUS      current
    DESCRIPTION
            "A unique value, greater than zero, for each chassis`s slot9."
    ::= { slot9ModuleEntry 1 }

slot9ModuleId OBJECT-TYPE
    SYNTAX      DisplayString (SIZE (0..32))
    MAX-ACCESS  read-only
    STATUS      current
    DESCRIPTION
            "the value of module`s id"
    ::= { slot9ModuleEntry 2 }
  
slot9ModuleIfNumber OBJECT-TYPE
    SYNTAX      Integer32(0..2147483647)
    MAX-ACCESS  read-only
    STATUS      current
    DESCRIPTION
            "The number of network interfaces (regardless of their
            current state) present on this system." 
    ::= { slot9ModuleEntry 3 } 
    
slot9ModuleIfTable OBJECT-TYPE
    SYNTAX      SEQUENCE OF Slot9ModuleIfEntry
    MAX-ACCESS  not-accessible
    STATUS      current
    DESCRIPTION
            "A list of interface entries.  The number of entries is
            given by the value of ifNumber."
    ::= { slot9Module 2 } 
    
slot9ModuleIfEntry OBJECT-TYPE
    SYNTAX      Slot9ModuleIfEntry
    MAX-ACCESS  not-accessible
    STATUS      current
    DESCRIPTION
            "An entry containing management information applicable to a
            particular interface."
    INDEX   { slot9ModuleifIndex }
    ::= { slot9ModuleIfTable 1 }
    
Slot9ModuleIfEntry ::=
    SEQUENCE {
        slot9ModuleifIndex                 InterfaceIndex,  
        slot9ModuleIfId                    DisplayString,  
        slot9ModuleifDescr                 DisplayString,           
        slot9ModuleifType                  IANAifType,   		
        slot9ModuleifMtu                   Integer32,                
        slot9ModuleifSpeed                 Counter64,               
        slot9ModuleifPhysAddress           PhysAddress,              
        slot9ModuleifAdminStatus           INTEGER,                  
        slot9ModuleifOperStatus            INTEGER,                  
        slot9ModuleifLastChange            TimeTicks,                
	slot9ModuleifInKbits   	           Counter64,
	slot9ModuleifOutKbits              Counter64,
        slot9ModuleifInOctets              Counter64,                
        slot9ModuleifInUcastPkts           Counter64,                
        slot9ModuleifInNUcastPkts          Counter64,   
        slot9ModuleifInDiscards            Counter64,
        slot9ModuleifInErrors              Counter64,
        slot9ModuleifInFcsErrorPkts        Counter64,
        slot9ModuleifInUnknownProtos       Counter64,	-- deprecated
        slot9ModuleifOutOctets             Counter64,
        slot9ModuleifOutUcastPkts          Counter64,
        slot9ModuleifOutNUcastPkts         Counter64,  -- deprecated
        slot9ModuleifOutDiscards           Counter64,
        slot9ModuleifOutErrors             Counter64,
        slot9ModuleifOutFcsErrorPkts       Counter64,
        slot9ModuleifOutQLen               Gauge32,    -- deprecated  
 	    slot9ModuleifInpps   	           Counter64,
	    slot9ModuleifOutpps              Counter64,       
        slot9ModuleifRxPower                DisplayString,
        slot9ModuleifTxPower                DisplayString,
        slot9ModuleifSpecific              OBJECT IDENTIFIER
    }         

slot9ModuleifIndex OBJECT-TYPE
    SYNTAX      InterfaceIndex
    MAX-ACCESS  read-only
    STATUS      current
    DESCRIPTION
            "A unique value, greater than zero, for each interface.  It
            is recommended that values are assigned contiguously
            starting from 1.  The value for each interface sub-layer
            must remain constant at least from one re-initialization of
            the entity's network management system to the next re-
            initialization."
    ::= { slot9ModuleIfEntry 1 }
    
slot9ModuleIfId OBJECT-TYPE
    SYNTAX      DisplayString (SIZE (0..32))
    MAX-ACCESS  read-only
    STATUS      current
    DESCRIPTION
            "the value of module`s id"
    ::= { slot9ModuleIfEntry 2 }
    
slot9ModuleifDescr OBJECT-TYPE
    SYNTAX      DisplayString (SIZE (0..255))
    MAX-ACCESS  read-only
    STATUS      current
    DESCRIPTION
            "A textual string containing information about the
            interface.  This string should include the name of the
            manufacturer, the product name and the version of the
            interface hardware/software."
    ::= { slot9ModuleIfEntry 3 }
    
slot9ModuleifType OBJECT-TYPE
    SYNTAX      IANAifType
    MAX-ACCESS  read-only
    STATUS      current
    DESCRIPTION
            "The type of interface.  Additional values for ifType are
            assigned by the Internet Assigned Numbers Authority (IANA),
            through updating the syntax of the IANAifType textual
            convention."
    ::= { slot9ModuleIfEntry 4 }

slot9ModuleifMtu OBJECT-TYPE
    SYNTAX      Integer32(1..2147483647)
    MAX-ACCESS  read-only
    STATUS      current
    DESCRIPTION
            "The size of the largest packet which can be sent/received
            on the interface, specified in octets.  For interfaces that
            are used for transmitting network datagrams, this is the
            size of the largest network datagram that can be sent on the
            interface."
    ::= { slot9ModuleIfEntry 5 }

slot9ModuleifSpeed OBJECT-TYPE
    SYNTAX      Counter64
    MAX-ACCESS  read-only
    STATUS      current
    DESCRIPTION
            "An estimate of the interface's current bandwidth in bits
            per second.  For interfaces which do not vary in bandwidth
            or for those where no accurate estimation can be made, this
            object should contain the nominal bandwidth. For a sub-layer
            which has no concept of bandwidth, this object should be zero."
    ::= { slot9ModuleIfEntry 6 }

slot9ModuleifPhysAddress OBJECT-TYPE
    SYNTAX      PhysAddress
    MAX-ACCESS  read-only
    STATUS      current
    DESCRIPTION
            "The interface's address at its protocol sub-layer.  For
            example, for an 802.x interface, this object normally
            contains a MAC address.  The interface's media-specific MIB
            must define the bit and byte ordering and the format of the
            value of this object.  For interfaces which do not have such
            an address (e.g., a serial line), this object should contain
            an octet string of zero length."
    ::= { slot9ModuleIfEntry 7 }
    
slot9ModuleifAdminStatus OBJECT-TYPE
    SYNTAX  INTEGER {
                up(1),       -- ready to pass packets
                down(2),
                testing(3)   -- in some test mode
            }
    MAX-ACCESS  read-write
    STATUS      current
    DESCRIPTION
            "The desired state of the interface.  The testing(3) state
            indicates that no operational packets can be passed.  When a
            managed system initializes, all interfaces start with
            ifAdminStatus in the down(2) state.  As a result of either
            explicit management action or per configuration information
            retained by the managed system, ifAdminStatus is then
            changed to either the up(1) or testing(3) states (or remains
            in the down(2) state)."
    ::= { slot9ModuleIfEntry 8 }

slot9ModuleifOperStatus OBJECT-TYPE
    SYNTAX  INTEGER {
                up(1),        -- ready to pass packets
                down(2),
                testing(3),   -- in some test mode
                unknown(4),   -- status can not be determined
                              -- for some reason.
                dormant(5),
                notPresent(6),    -- some component is missing
                lowerLayerDown(7) -- down due to state of
                                  -- lower-layer interface(s)
            }
    MAX-ACCESS  read-only
    STATUS      current
    DESCRIPTION
            "The current operational state of the interface.  The
            testing(3) state indicates that no operational packets can
            be passed.  If ifAdminStatus is down(2) then ifOperStatus
            should be down(2).  If ifAdminStatus is changed to up(1)
            then ifOperStatus should change to up(1) if the interface is
            ready to transmit and receive network traffic; it should
            change to dormant(5) if the interface is waiting for
            external actions (such as a serial line waiting for an
            incoming connection); it should remain in the down(2) state
            if and only if there is a fault that prevents it from going
            to the up(1) state; it should remain in the notPresent(6)
            state if the interface has missing (typically, hardware)
            components."
    ::= { slot9ModuleIfEntry 9 }

slot9ModuleifLastChange OBJECT-TYPE
    SYNTAX      TimeTicks
    MAX-ACCESS  read-only
    STATUS      current
    DESCRIPTION
            "The value of sysUpTime at the time the interface entered
            its current operational state.  If the current state was
            entered prior to the last re-initialization of the local
            network management subsystem, then this object contains a
            zero value."
    ::= { slot9ModuleIfEntry 10 }

slot9ModuleifInKbits OBJECT-TYPE
    SYNTAX      Counter64
    MAX-ACCESS  read-only
    STATUS      current
    DESCRIPTION
            "The real time rate received on the interface, in Kbits
	    format.

            Discontinuities in the value of this counter can occur at
            re-initialization of the management system, and at other
            times as indicated by the value of
            ifCounterDiscontinuityTime."
    ::= { slot9ModuleIfEntry 11 }

slot9ModuleifOutKbits OBJECT-TYPE
    SYNTAX      Counter64
    MAX-ACCESS  read-only
    STATUS      current
    DESCRIPTION
            "The real time rate send on the interface, in Kbits
	    format.

            Discontinuities in the value of this counter can occur at
            re-initialization of the management system, and at other
            times as indicated by the value of
            ifCounterDiscontinuityTime."
    ::= { slot9ModuleIfEntry 12 }

slot9ModuleifInOctets OBJECT-TYPE
    SYNTAX      Counter64
    MAX-ACCESS  read-only
    STATUS      current
    DESCRIPTION
            "The total number of octets received on the interface,
            including framing characters.

            Discontinuities in the value of this counter can occur at
            re-initialization of the management system, and at other
            times as indicated by the value of
            ifCounterDiscontinuityTime."
    ::= { slot9ModuleIfEntry 13 }

slot9ModuleifInUcastPkts OBJECT-TYPE
    SYNTAX      Counter64
    MAX-ACCESS  read-only
    STATUS      current
    DESCRIPTION
            "The number of packets, delivered by this sub-layer to a
            higher (sub-)layer, which were not addressed to a multicast
            or broadcast address at this sub-layer.

            Discontinuities in the value of this counter can occur at
            re-initialization of the management system, and at other
            times as indicated by the value of
            ifCounterDiscontinuityTime."
    ::= { slot9ModuleIfEntry 14 }

slot9ModuleifInNUcastPkts OBJECT-TYPE
    SYNTAX  Counter64
    MAX-ACCESS  read-only
    STATUS      current
    DESCRIPTION
            "The number of packets, delivered by this sub-layer to a
            higher (sub-)layer, which were addressed to a multicast or
            broadcast address at this sub-layer.

            Discontinuities in the value of this counter can occur at
            re-initialization of the management system, and at other
            times as indicated by the value of
            ifCounterDiscontinuityTime.

            This object is deprecated in favour of ifInMulticastPkts and
            ifInBroadcastPkts."
    ::= { slot9ModuleIfEntry 15 }

slot9ModuleifInDiscards OBJECT-TYPE
    SYNTAX      Counter64
    MAX-ACCESS  read-only
    STATUS      current
    DESCRIPTION
            "The number of inbound packets which were chosen to be
            discarded even though no errors had been detected to prevent

            their being deliverable to a higher-layer protocol.  One
            possible reason for discarding such a packet could be to
            free up buffer space.

            Discontinuities in the value of this counter can occur at
            re-initialization of the management system, and at other
            times as indicated by the value of
            ifCounterDiscontinuityTime."
    ::= { slot9ModuleIfEntry 16 }

slot9ModuleifInErrors OBJECT-TYPE
    SYNTAX      Counter64
    MAX-ACCESS  read-only
    STATUS      current
    DESCRIPTION
            "For packet-oriented interfaces, the number of inbound
            packets that contained errors preventing them from being
            deliverable to a higher-layer protocol.  For character-
            oriented or fixed-length interfaces, the number of inbound
            transmission units that contained errors preventing them
            from being deliverable to a higher-layer protocol.

            Discontinuities in the value of this counter can occur at
            re-initialization of the management system, and at other
            times as indicated by the value of
            ifCounterDiscontinuityTime."
    ::= { slot9ModuleIfEntry 17 }

slot9ModuleifInFcsErrorPkts OBJECT-TYPE
    SYNTAX      Counter64
    MAX-ACCESS  read-only
    STATUS      current
    DESCRIPTION
            "FCS error pakets."
    ::= { slot9ModuleIfEntry 18 }

slot9ModuleifInUnknownProtos OBJECT-TYPE
    SYNTAX      Counter64
    MAX-ACCESS  read-only
    STATUS      current
    DESCRIPTION
            "For packet-oriented interfaces, the number of packets
            received via the interface which were discarded because of
            an unknown or unsupported protocol.  For character-oriented
            or fixed-length interfaces that support protocol
            multiplexing the number of transmission units received via
            the interface which were discarded because of an unknown or
            unsupported protocol.  For any interface that does not
            support protocol multiplexing, this counter will always be
            0.

            Discontinuities in the value of this counter can occur at
            re-initialization of the management system, and at other
            times as indicated by the value of
            ifCounterDiscontinuityTime."
    ::= { slot9ModuleIfEntry 19 }

slot9ModuleifOutOctets OBJECT-TYPE
    SYNTAX      Counter64
    MAX-ACCESS  read-only
    STATUS      current
    DESCRIPTION
            "The total number of octets transmitted out of the
            interface, including framing characters.

            Discontinuities in the value of this counter can occur at
            re-initialization of the management system, and at other
            times as indicated by the value of
            ifCounterDiscontinuityTime."
    ::= { slot9ModuleIfEntry 20 }

slot9ModuleifOutUcastPkts OBJECT-TYPE
    SYNTAX      Counter64
    MAX-ACCESS  read-only
    STATUS      current
    DESCRIPTION
            "The total number of packets that higher-level protocols
            requested be transmitted, and which were not addressed to a
            multicast or broadcast address at this sub-layer, including
            those that were discarded or not sent.

            Discontinuities in the value of this counter can occur at
            re-initialization of the management system, and at other
            times as indicated by the value of
            ifCounterDiscontinuityTime."
    ::= { slot9ModuleIfEntry 21 }

slot9ModuleifOutNUcastPkts OBJECT-TYPE
    SYNTAX      Counter64
    MAX-ACCESS  read-only
    STATUS      deprecated
    DESCRIPTION
            "The total number of packets that higher-level protocols
            requested be transmitted, and which were addressed to a
            multicast or broadcast address at this sub-layer, including
            those that were discarded or not sent.

            Discontinuities in the value of this counter can occur at
            re-initialization of the management system, and at other
            times as indicated by the value of
            ifCounterDiscontinuityTime.

            This object is deprecated in favour of ifOutMulticastPkts
            and ifOutBroadcastPkts."
    ::= { slot9ModuleIfEntry 22 }

slot9ModuleifOutDiscards OBJECT-TYPE
    SYNTAX      Counter64
    MAX-ACCESS  read-only
    STATUS      current
    DESCRIPTION
            "The number of outbound packets which were chosen to be
            discarded even though no errors had been detected to prevent
            their being transmitted.  One possible reason for discarding
            such a packet could be to free up buffer space.

            Discontinuities in the value of this counter can occur at
            re-initialization of the management system, and at other
            times as indicated by the value of
            ifCounterDiscontinuityTime."
    ::= { slot9ModuleIfEntry 23 }

slot9ModuleifOutErrors OBJECT-TYPE
    SYNTAX      Counter64
    MAX-ACCESS  read-only
    STATUS      current
    DESCRIPTION
            "For packet-oriented interfaces, the number of outbound
            packets that could not be transmitted because of errors.
            For character-oriented or fixed-length interfaces, the
            number of outbound transmission units that could not be
            transmitted because of errors.

            Discontinuities in the value of this counter can occur at
            re-initialization of the management system, and at other
            times as indicated by the value of
            ifCounterDiscontinuityTime."
    ::= { slot9ModuleIfEntry 24 }

slot9ModuleifOutFcsErrorPkts OBJECT-TYPE
    SYNTAX      Counter64
    MAX-ACCESS  read-only
    STATUS      current
    DESCRIPTION
            "FCS error pakets."
    ::= { slot9ModuleIfEntry 25 }

slot9ModuleifOutQLen OBJECT-TYPE
    SYNTAX      Gauge32
    MAX-ACCESS  read-only
    STATUS      deprecated
    DESCRIPTION
            "The length of the output packet queue (in packets)."
    ::= { slot9ModuleIfEntry 26 }

slot9ModuleifInpps OBJECT-TYPE
    SYNTAX      Counter64
    MAX-ACCESS  read-only
    STATUS      current
    DESCRIPTION
            "The real time rate received on the interface, in pps
	    format.

            Discontinuities in the value of this counter can occur at
            re-initialization of the management system, and at other
            times as indicated by the value of
            ifCounterDiscontinuityTime."
    ::= { slot9ModuleIfEntry 27 }

slot9ModuleifOutpps OBJECT-TYPE
    SYNTAX      Counter64
    MAX-ACCESS  read-only
    STATUS      current
    DESCRIPTION
            "The real time rate send on the interface, in pps
	    format.

            Discontinuities in the value of this counter can occur at
            re-initialization of the management system, and at other
            times as indicated by the value of
            ifCounterDiscontinuityTime."
    ::= { slot9ModuleIfEntry 28 }

slot9ModuleifRxPower OBJECT-TYPE
    SYNTAX      DisplayString (SIZE (0..255))
    MAX-ACCESS  read-only
    STATUS      current
    DESCRIPTION
            "the value of interface's received power, in dbm format."
    ::= { slot9ModuleIfEntry 29 }
    
slot9ModuleifTxPower OBJECT-TYPE
    SYNTAX      DisplayString (SIZE (0..255))
    MAX-ACCESS  read-only
    STATUS      current
    DESCRIPTION
            "the value of interface's send power, in dbm format."
    ::= { slot9ModuleIfEntry 30 }

slot9ModuleifSpecific OBJECT-TYPE
    SYNTAX      OBJECT IDENTIFIER
    MAX-ACCESS  read-only
    STATUS      deprecated
    DESCRIPTION
            "A reference to MIB definitions specific to the particular
            media being used to realize the interface.  It is

            recommended that this value point to an instance of a MIB
            object in the media-specific MIB, i.e., that this object
            have the semantics associated with the InstancePointer
            textual convention defined in RFC 2579.  In fact, it is
            recommended that the media-specific MIB specify what value
            ifSpecific should/can take for values of ifType.  If no MIB
            definitions specific to the particular media are available,
            the value should be set to the OBJECT IDENTIFIER { 0 0 }."
    ::= { slot9ModuleIfEntry 31 }  
    
-- slot 10 --

-- slot10Table --

slot10Table OBJECT-TYPE
    SYNTAX      SEQUENCE OF Slot10Entry
    MAX-ACCESS  not-accessible
    STATUS      current
    DESCRIPTION
            "A list of all slot10Type's utilization."
    ::= { slot10 1 }  

slot10Entry OBJECT-TYPE
    SYNTAX      Slot10Entry
    MAX-ACCESS  not-accessible
    STATUS      current
    DESCRIPTION
            "An entry contains a slot10's utilization."
    INDEX   { slot10Index }
    ::= { slot10Table 1 }

Slot10Entry ::=
    SEQUENCE {     
		slot10Index                       Integer32,
		slot10Type                        DisplayString,
		slot10Status                      DisplayString,		
		slot10Id                          Integer32
    }  

slot10Index OBJECT-TYPE
    SYNTAX      Integer32 (1..2147483647)
    MAX-ACCESS  not-accessible
    STATUS      current
    DESCRIPTION
            "A unique value, greater than zero, for each chassis`s slot10."
    ::= { slot10Entry 1 }

slot10Type OBJECT-TYPE
    SYNTAX      DisplayString (SIZE (0..255))
    MAX-ACCESS  read-only
    STATUS      current
    DESCRIPTION
            "the slot10Type of each chassis."
    ::= { slot10Entry 2 }

slot10Status OBJECT-TYPE
    SYNTAX      DisplayString (SIZE (0..255))
    MAX-ACCESS  read-only
    STATUS      current
    DESCRIPTION
            "A string to describe the board status." 
    ::= { slot10Entry 3 }   

slot10Id OBJECT-TYPE
    SYNTAX      Integer32
    MAX-ACCESS  read-only
    STATUS      current
    DESCRIPTION
            "slot id."
    ::= { slot10Entry 4 }

slot10Module OBJECT IDENTIFIER ::= { slot10 2 }

-- slot10ModuleTable --
slot10ModuleTable OBJECT-TYPE
    SYNTAX      SEQUENCE OF Slot10ModuleEntry
    MAX-ACCESS  not-accessible
    STATUS      current
    DESCRIPTION
            "A list of all slot10Module's utilization."
    ::= { slot10Module 1 }  

slot10ModuleEntry OBJECT-TYPE
    SYNTAX      Slot10ModuleEntry
    MAX-ACCESS  not-accessible
    STATUS      current
    DESCRIPTION
            "An entry contains a slot10Module's utilization."
    INDEX   { slot10ModuleIndex }
    ::= { slot10ModuleTable 1 }

Slot10ModuleEntry ::=
    SEQUENCE {     
		slot10ModuleIndex                       Integer32,
		slot10ModuleId                           DisplayString,  
		slot10ModuleIfNumber                     Integer32		
    } 

slot10ModuleIndex OBJECT-TYPE
    SYNTAX      Integer32 (1..2147483647)
    MAX-ACCESS  not-accessible
    STATUS      current
    DESCRIPTION
            "A unique value, greater than zero, for each chassis`s slot10."
    ::= { slot10ModuleEntry 1 }

slot10ModuleId OBJECT-TYPE
    SYNTAX      DisplayString (SIZE (0..32))
    MAX-ACCESS  read-only
    STATUS      current
    DESCRIPTION
            "the value of module`s id"
    ::= { slot10ModuleEntry 2 }
  
slot10ModuleIfNumber OBJECT-TYPE
    SYNTAX      Integer32(0..2147483647)
    MAX-ACCESS  read-only
    STATUS      current
    DESCRIPTION
            "The number of network interfaces (regardless of their
            current state) present on this system." 
    ::= { slot10ModuleEntry 3 } 
    
slot10ModuleIfTable OBJECT-TYPE
    SYNTAX      SEQUENCE OF Slot10ModuleIfEntry
    MAX-ACCESS  not-accessible
    STATUS      current
    DESCRIPTION
            "A list of interface entries.  The number of entries is
            given by the value of ifNumber."
    ::= { slot10Module 2 } 
    
slot10ModuleIfEntry OBJECT-TYPE
    SYNTAX      Slot10ModuleIfEntry
    MAX-ACCESS  not-accessible
    STATUS      current
    DESCRIPTION
            "An entry containing management information applicable to a
            particular interface."
    INDEX   { slot10ModuleifIndex }
    ::= { slot10ModuleIfTable 1 }
    
Slot10ModuleIfEntry ::=
    SEQUENCE {
        slot10ModuleifIndex                 InterfaceIndex,  
        slot10ModuleIfId                    DisplayString,  
        slot10ModuleifDescr                 DisplayString,           
        slot10ModuleifType                  IANAifType,   		
        slot10ModuleifMtu                   Integer32,                
        slot10ModuleifSpeed                 Counter64,               
        slot10ModuleifPhysAddress           PhysAddress,              
        slot10ModuleifAdminStatus           INTEGER,                  
        slot10ModuleifOperStatus            INTEGER,                  
        slot10ModuleifLastChange            TimeTicks,                
	slot10ModuleifInKbits   	    Counter64,
	slot10ModuleifOutKbits              Counter64,
        slot10ModuleifInOctets              Counter64,                
        slot10ModuleifInUcastPkts           Counter64,                
        slot10ModuleifInNUcastPkts          Counter64,  
        slot10ModuleifInDiscards            Counter64,
        slot10ModuleifInErrors              Counter64,
        slot10ModuleifInFcsErrorPkts        Counter64,
        slot10ModuleifInUnknownProtos       Counter64,	-- deprecated
        slot10ModuleifOutOctets             Counter64,
        slot10ModuleifOutUcastPkts          Counter64,
        slot10ModuleifOutNUcastPkts         Counter64,  -- deprecated
        slot10ModuleifOutDiscards           Counter64,
        slot10ModuleifOutErrors             Counter64,
        slot10ModuleifOutFcsErrorPkts       Counter64,
        slot10ModuleifOutQLen               Gauge32,    -- deprecated  
	    slot10ModuleifInpps   	    Counter64,
	    slot10ModuleifOutpps              Counter64,        
        slot10ModuleifRxPower                DisplayString,
        slot10ModuleifTxPower                DisplayString,
        slot10ModuleifSpecific              OBJECT IDENTIFIER
    }         

slot10ModuleifIndex OBJECT-TYPE
    SYNTAX      InterfaceIndex
    MAX-ACCESS  read-only
    STATUS      current
    DESCRIPTION
            "A unique value, greater than zero, for each interface.  It
            is recommended that values are assigned contiguously
            starting from 1.  The value for each interface sub-layer
            must remain constant at least from one re-initialization of
            the entity's network management system to the next re-
            initialization."
    ::= { slot10ModuleIfEntry 1 }
    
slot10ModuleIfId OBJECT-TYPE
    SYNTAX      DisplayString (SIZE (0..32))
    MAX-ACCESS  read-only
    STATUS      current
    DESCRIPTION
            "the value of module`s id"
    ::= { slot10ModuleIfEntry 2 }
    
slot10ModuleifDescr OBJECT-TYPE
    SYNTAX      DisplayString (SIZE (0..255))
    MAX-ACCESS  read-only
    STATUS      current
    DESCRIPTION
            "A textual string containing information about the
            interface.  This string should include the name of the
            manufacturer, the product name and the version of the
            interface hardware/software."
    ::= { slot10ModuleIfEntry 3 }
    
slot10ModuleifType OBJECT-TYPE
    SYNTAX      IANAifType
    MAX-ACCESS  read-only
    STATUS      current
    DESCRIPTION
            "The type of interface.  Additional values for ifType are
            assigned by the Internet Assigned Numbers Authority (IANA),
            through updating the syntax of the IANAifType textual
            convention."
    ::= { slot10ModuleIfEntry 4 }

slot10ModuleifMtu OBJECT-TYPE
    SYNTAX      Integer32(1..2147483647)
    MAX-ACCESS  read-only
    STATUS      current
    DESCRIPTION
            "The size of the largest packet which can be sent/received
            on the interface, specified in octets.  For interfaces that
            are used for transmitting network datagrams, this is the
            size of the largest network datagram that can be sent on the
            interface."
    ::= { slot10ModuleIfEntry 5 }

slot10ModuleifSpeed OBJECT-TYPE
    SYNTAX      Counter64
    MAX-ACCESS  read-only
    STATUS      current
    DESCRIPTION
            "An estimate of the interface's current bandwidth in bits
            per second.  For interfaces which do not vary in bandwidth
            or for those where no accurate estimation can be made, this
            object should contain the nominal bandwidth. For a sub-layer
            which has no concept of bandwidth, this object should be zero."
    ::= { slot10ModuleIfEntry 6 }

slot10ModuleifPhysAddress OBJECT-TYPE
    SYNTAX      PhysAddress
    MAX-ACCESS  read-only
    STATUS      current
    DESCRIPTION
            "The interface's address at its protocol sub-layer.  For
            example, for an 802.x interface, this object normally
            contains a MAC address.  The interface's media-specific MIB
            must define the bit and byte ordering and the format of the
            value of this object.  For interfaces which do not have such
            an address (e.g., a serial line), this object should contain
            an octet string of zero length."
    ::= { slot10ModuleIfEntry 7 }
    
slot10ModuleifAdminStatus OBJECT-TYPE
    SYNTAX  INTEGER {
                up(1),       -- ready to pass packets
                down(2),
                testing(3)   -- in some test mode
            }
    MAX-ACCESS  read-write
    STATUS      current
    DESCRIPTION
            "The desired state of the interface.  The testing(3) state
            indicates that no operational packets can be passed.  When a
            managed system initializes, all interfaces start with
            ifAdminStatus in the down(2) state.  As a result of either
            explicit management action or per configuration information
            retained by the managed system, ifAdminStatus is then
            changed to either the up(1) or testing(3) states (or remains
            in the down(2) state)."
    ::= { slot10ModuleIfEntry 8 }

slot10ModuleifOperStatus OBJECT-TYPE
    SYNTAX  INTEGER {
                up(1),        -- ready to pass packets
                down(2),
                testing(3),   -- in some test mode
                unknown(4),   -- status can not be determined
                              -- for some reason.
                dormant(5),
                notPresent(6),    -- some component is missing
                lowerLayerDown(7) -- down due to state of
                                  -- lower-layer interface(s)
            }
    MAX-ACCESS  read-only
    STATUS      current
    DESCRIPTION
            "The current operational state of the interface.  The
            testing(3) state indicates that no operational packets can
            be passed.  If ifAdminStatus is down(2) then ifOperStatus
            should be down(2).  If ifAdminStatus is changed to up(1)
            then ifOperStatus should change to up(1) if the interface is
            ready to transmit and receive network traffic; it should
            change to dormant(5) if the interface is waiting for
            external actions (such as a serial line waiting for an
            incoming connection); it should remain in the down(2) state
            if and only if there is a fault that prevents it from going
            to the up(1) state; it should remain in the notPresent(6)
            state if the interface has missing (typically, hardware)
            components."
    ::= { slot10ModuleIfEntry 9 }

slot10ModuleifLastChange OBJECT-TYPE
    SYNTAX      TimeTicks
    MAX-ACCESS  read-only
    STATUS      current
    DESCRIPTION
            "The value of sysUpTime at the time the interface entered
            its current operational state.  If the current state was
            entered prior to the last re-initialization of the local
            network management subsystem, then this object contains a
            zero value."
    ::= { slot10ModuleIfEntry 10 }

slot10ModuleifInKbits OBJECT-TYPE
    SYNTAX      Counter64
    MAX-ACCESS  read-only
    STATUS      current
    DESCRIPTION
            "The real time rate received on the interface, in Kbits
	    format.

            Discontinuities in the value of this counter can occur at
            re-initialization of the management system, and at other
            times as indicated by the value of
            ifCounterDiscontinuityTime."
    ::= { slot10ModuleIfEntry 11 }

slot10ModuleifOutKbits OBJECT-TYPE
    SYNTAX      Counter64
    MAX-ACCESS  read-only
    STATUS      current
    DESCRIPTION
            "The real time rate send on the interface, in Kbits
	    format.

            Discontinuities in the value of this counter can occur at
            re-initialization of the management system, and at other
            times as indicated by the value of
            ifCounterDiscontinuityTime."
    ::= { slot10ModuleIfEntry 12 }

slot10ModuleifInOctets OBJECT-TYPE
    SYNTAX      Counter64
    MAX-ACCESS  read-only
    STATUS      current
    DESCRIPTION
            "The total number of octets received on the interface,
            including framing characters.

            Discontinuities in the value of this counter can occur at
            re-initialization of the management system, and at other
            times as indicated by the value of
            ifCounterDiscontinuityTime."
    ::= { slot10ModuleIfEntry 13 }

slot10ModuleifInUcastPkts OBJECT-TYPE
    SYNTAX      Counter64
    MAX-ACCESS  read-only
    STATUS      current
    DESCRIPTION
            "The number of packets, delivered by this sub-layer to a
            higher (sub-)layer, which were not addressed to a multicast
            or broadcast address at this sub-layer.

            Discontinuities in the value of this counter can occur at
            re-initialization of the management system, and at other
            times as indicated by the value of
            ifCounterDiscontinuityTime."
    ::= { slot10ModuleIfEntry 14 }

slot10ModuleifInNUcastPkts OBJECT-TYPE
    SYNTAX  Counter64
    MAX-ACCESS  read-only
    STATUS      current
    DESCRIPTION
            "The number of packets, delivered by this sub-layer to a
            higher (sub-)layer, which were addressed to a multicast or
            broadcast address at this sub-layer.

            Discontinuities in the value of this counter can occur at
            re-initialization of the management system, and at other
            times as indicated by the value of
            ifCounterDiscontinuityTime.

            This object is deprecated in favour of ifInMulticastPkts and
            ifInBroadcastPkts."
    ::= { slot10ModuleIfEntry 15 }

slot10ModuleifInDiscards OBJECT-TYPE
    SYNTAX      Counter64
    MAX-ACCESS  read-only
    STATUS      current
    DESCRIPTION
            "The number of inbound packets which were chosen to be
            discarded even though no errors had been detected to prevent

            their being deliverable to a higher-layer protocol.  One
            possible reason for discarding such a packet could be to
            free up buffer space.

            Discontinuities in the value of this counter can occur at
            re-initialization of the management system, and at other
            times as indicated by the value of
            ifCounterDiscontinuityTime."
    ::= { slot10ModuleIfEntry 16 }

slot10ModuleifInErrors OBJECT-TYPE
    SYNTAX      Counter64
    MAX-ACCESS  read-only
    STATUS      current
    DESCRIPTION
            "For packet-oriented interfaces, the number of inbound
            packets that contained errors preventing them from being
            deliverable to a higher-layer protocol.  For character-
            oriented or fixed-length interfaces, the number of inbound
            transmission units that contained errors preventing them
            from being deliverable to a higher-layer protocol.

            Discontinuities in the value of this counter can occur at
            re-initialization of the management system, and at other
            times as indicated by the value of
            ifCounterDiscontinuityTime."
    ::= { slot10ModuleIfEntry 17 }

slot10ModuleifInFcsErrorPkts OBJECT-TYPE
    SYNTAX      Counter64
    MAX-ACCESS  read-only
    STATUS      current
    DESCRIPTION
            "FCS error pakets."
    ::= { slot10ModuleIfEntry 18 }

slot10ModuleifInUnknownProtos OBJECT-TYPE
    SYNTAX      Counter64
    MAX-ACCESS  read-only
    STATUS      current
    DESCRIPTION
            "For packet-oriented interfaces, the number of packets
            received via the interface which were discarded because of
            an unknown or unsupported protocol.  For character-oriented
            or fixed-length interfaces that support protocol
            multiplexing the number of transmission units received via
            the interface which were discarded because of an unknown or
            unsupported protocol.  For any interface that does not
            support protocol multiplexing, this counter will always be
            0.

            Discontinuities in the value of this counter can occur at
            re-initialization of the management system, and at other
            times as indicated by the value of
            ifCounterDiscontinuityTime."
    ::= { slot10ModuleIfEntry 19 }

slot10ModuleifOutOctets OBJECT-TYPE
    SYNTAX      Counter64
    MAX-ACCESS  read-only
    STATUS      current
    DESCRIPTION
            "The total number of octets transmitted out of the
            interface, including framing characters.

            Discontinuities in the value of this counter can occur at
            re-initialization of the management system, and at other
            times as indicated by the value of
            ifCounterDiscontinuityTime."
    ::= { slot10ModuleIfEntry 20 }

slot10ModuleifOutUcastPkts OBJECT-TYPE
    SYNTAX      Counter64
    MAX-ACCESS  read-only
    STATUS      current
    DESCRIPTION
            "The total number of packets that higher-level protocols
            requested be transmitted, and which were not addressed to a
            multicast or broadcast address at this sub-layer, including
            those that were discarded or not sent.

            Discontinuities in the value of this counter can occur at
            re-initialization of the management system, and at other
            times as indicated by the value of
            ifCounterDiscontinuityTime."
    ::= { slot10ModuleIfEntry 21 }

slot10ModuleifOutNUcastPkts OBJECT-TYPE
    SYNTAX      Counter64
    MAX-ACCESS  read-only
    STATUS      deprecated
    DESCRIPTION
            "The total number of packets that higher-level protocols
            requested be transmitted, and which were addressed to a
            multicast or broadcast address at this sub-layer, including
            those that were discarded or not sent.

            Discontinuities in the value of this counter can occur at
            re-initialization of the management system, and at other
            times as indicated by the value of
            ifCounterDiscontinuityTime.

            This object is deprecated in favour of ifOutMulticastPkts
            and ifOutBroadcastPkts."
    ::= { slot10ModuleIfEntry 22 }

slot10ModuleifOutDiscards OBJECT-TYPE
    SYNTAX      Counter64
    MAX-ACCESS  read-only
    STATUS      current
    DESCRIPTION
            "The number of outbound packets which were chosen to be
            discarded even though no errors had been detected to prevent
            their being transmitted.  One possible reason for discarding
            such a packet could be to free up buffer space.

            Discontinuities in the value of this counter can occur at
            re-initialization of the management system, and at other
            times as indicated by the value of
            ifCounterDiscontinuityTime."
    ::= { slot10ModuleIfEntry 23 }

slot10ModuleifOutErrors OBJECT-TYPE
    SYNTAX      Counter64
    MAX-ACCESS  read-only
    STATUS      current
    DESCRIPTION
            "For packet-oriented interfaces, the number of outbound
            packets that could not be transmitted because of errors.
            For character-oriented or fixed-length interfaces, the
            number of outbound transmission units that could not be
            transmitted because of errors.

            Discontinuities in the value of this counter can occur at
            re-initialization of the management system, and at other
            times as indicated by the value of
            ifCounterDiscontinuityTime."
    ::= { slot10ModuleIfEntry 24 }

slot10ModuleifOutFcsErrorPkts OBJECT-TYPE
    SYNTAX      Counter64
    MAX-ACCESS  read-only
    STATUS      current
    DESCRIPTION
            "FCS error pakets."
    ::= { slot10ModuleIfEntry 25 }

slot10ModuleifOutQLen OBJECT-TYPE
    SYNTAX      Gauge32
    MAX-ACCESS  read-only
    STATUS      deprecated
    DESCRIPTION
            "The length of the output packet queue (in packets)."
    ::= { slot10ModuleIfEntry 26 }

slot10ModuleifInpps OBJECT-TYPE
    SYNTAX      Counter64
    MAX-ACCESS  read-only
    STATUS      current
    DESCRIPTION
            "The real time rate received on the interface, in pps
	    format.

            Discontinuities in the value of this counter can occur at
            re-initialization of the management system, and at other
            times as indicated by the value of
            ifCounterDiscontinuityTime."
    ::= { slot10ModuleIfEntry 27 }

slot10ModuleifOutpps OBJECT-TYPE
    SYNTAX      Counter64
    MAX-ACCESS  read-only
    STATUS      current
    DESCRIPTION
            "The real time rate send on the interface, in pps
	    format.

            Discontinuities in the value of this counter can occur at
            re-initialization of the management system, and at other
            times as indicated by the value of
            ifCounterDiscontinuityTime."
    ::= { slot10ModuleIfEntry 28 }

slot10ModuleifRxPower OBJECT-TYPE
    SYNTAX      DisplayString (SIZE (0..255))
    MAX-ACCESS  read-only
    STATUS      current
    DESCRIPTION
            "the value of interface's received power, in dbm format."
    ::= { slot10ModuleIfEntry 29 }
    
slot10ModuleifTxPower OBJECT-TYPE
    SYNTAX      DisplayString (SIZE (0..255))
    MAX-ACCESS  read-only
    STATUS      current
    DESCRIPTION
            "the value of interface's send power, in dbm format."
    ::= { slot10ModuleIfEntry 30 }

slot10ModuleifSpecific OBJECT-TYPE
    SYNTAX      OBJECT IDENTIFIER
    MAX-ACCESS  read-only
    STATUS      deprecated
    DESCRIPTION
            "A reference to MIB definitions specific to the particular
            media being used to realize the interface.  It is

            recommended that this value point to an instance of a MIB
            object in the media-specific MIB, i.e., that this object
            have the semantics associated with the InstancePointer
            textual convention defined in RFC 2579.  In fact, it is
            recommended that the media-specific MIB specify what value
            ifSpecific should/can take for values of ifType.  If no MIB
            definitions specific to the particular media are available,
            the value should be set to the OBJECT IDENTIFIER { 0 0 }."
    ::= { slot10ModuleIfEntry 31 }  
    
-- slot 11 --

-- slot11Table --

slot11Table OBJECT-TYPE
    SYNTAX      SEQUENCE OF Slot11Entry
    MAX-ACCESS  not-accessible
    STATUS      current
    DESCRIPTION
            "A list of all slot11Type's utilization."
    ::= { slot11 1 }  

slot11Entry OBJECT-TYPE
    SYNTAX      Slot11Entry
    MAX-ACCESS  not-accessible
    STATUS      current
    DESCRIPTION
            "An entry contains a slot11's utilization."
    INDEX   { slot11Index }
    ::= { slot11Table 1 }

Slot11Entry ::=
    SEQUENCE {     
		slot11Index                       Integer32,
		slot11Type                        DisplayString,
		slot11Status                      DisplayString,		
		slot11Id                          Integer32
    }  

slot11Index OBJECT-TYPE
    SYNTAX      Integer32 (1..2147483647)
    MAX-ACCESS  not-accessible
    STATUS      current
    DESCRIPTION
            "A unique value, greater than zero, for each chassis`s slot11."
    ::= { slot11Entry 1 }

slot11Type OBJECT-TYPE
    SYNTAX      DisplayString (SIZE (0..255))
    MAX-ACCESS  read-only
    STATUS      current
    DESCRIPTION
            "the slot11Type of each chassis."
    ::= { slot11Entry 2 }

slot11Status OBJECT-TYPE
    SYNTAX      DisplayString (SIZE (0..255))
    MAX-ACCESS  read-only
    STATUS      current
    DESCRIPTION
            "A string to describe the board status." 
    ::= { slot11Entry 3 }   

slot11Id OBJECT-TYPE
    SYNTAX      Integer32
    MAX-ACCESS  read-only
    STATUS      current
    DESCRIPTION
            "slot id."
    ::= { slot11Entry 4 }

slot11Module OBJECT IDENTIFIER ::= { slot11 2 }

-- slot11ModuleTable --
slot11ModuleTable OBJECT-TYPE
    SYNTAX      SEQUENCE OF Slot11ModuleEntry
    MAX-ACCESS  not-accessible
    STATUS      current
    DESCRIPTION
            "A list of all slot11Module's utilization."
    ::= { slot11Module 1 }  

slot11ModuleEntry OBJECT-TYPE
    SYNTAX      Slot11ModuleEntry
    MAX-ACCESS  not-accessible
    STATUS      current
    DESCRIPTION
            "An entry contains a slot11Module's utilization."
    INDEX   { slot11ModuleIndex }
    ::= { slot11ModuleTable 1 }

Slot11ModuleEntry ::=
    SEQUENCE {     
		slot11ModuleIndex                       Integer32,
		slot11ModuleId                           DisplayString,  
		slot11ModuleIfNumber                     Integer32		
    } 

slot11ModuleIndex OBJECT-TYPE
    SYNTAX      Integer32 (1..2147483647)
    MAX-ACCESS  not-accessible
    STATUS      current
    DESCRIPTION
            "A unique value, greater than zero, for each chassis`s slot11."
    ::= { slot11ModuleEntry 1 }

slot11ModuleId OBJECT-TYPE
    SYNTAX      DisplayString (SIZE (0..32))
    MAX-ACCESS  read-only
    STATUS      current
    DESCRIPTION
            "the value of module`s id"
    ::= { slot11ModuleEntry 2 }
  
slot11ModuleIfNumber OBJECT-TYPE
    SYNTAX      Integer32(0..2147483647)
    MAX-ACCESS  read-only
    STATUS      current
    DESCRIPTION
            "The number of network interfaces (regardless of their
            current state) present on this system." 
    ::= { slot11ModuleEntry 3 } 
    
slot11ModuleIfTable OBJECT-TYPE
    SYNTAX      SEQUENCE OF Slot11ModuleIfEntry
    MAX-ACCESS  not-accessible
    STATUS      current
    DESCRIPTION
            "A list of interface entries.  The number of entries is
            given by the value of ifNumber."
    ::= { slot11Module 2 } 
    
slot11ModuleIfEntry OBJECT-TYPE
    SYNTAX      Slot11ModuleIfEntry
    MAX-ACCESS  not-accessible
    STATUS      current
    DESCRIPTION
            "An entry containing management information applicable to a
            particular interface."
    INDEX   { slot11ModuleifIndex }
    ::= { slot11ModuleIfTable 1 }
    
Slot11ModuleIfEntry ::=
    SEQUENCE {
        slot11ModuleifIndex                 InterfaceIndex,  
        slot11ModuleIfId                    DisplayString,  
        slot11ModuleifDescr                 DisplayString,           
        slot11ModuleifType                  IANAifType,   		
        slot11ModuleifMtu                   Integer32,                
        slot11ModuleifSpeed                 Counter64,               
        slot11ModuleifPhysAddress           PhysAddress,              
        slot11ModuleifAdminStatus           INTEGER,                  
        slot11ModuleifOperStatus            INTEGER,                  
        slot11ModuleifLastChange            TimeTicks,                
	slot11ModuleifInKbits   	    Counter64,
	slot11ModuleifOutKbits              Counter64,
        slot11ModuleifInOctets              Counter64,                
        slot11ModuleifInUcastPkts           Counter64,                
        slot11ModuleifInNUcastPkts          Counter64,  
        slot11ModuleifInDiscards            Counter64,
        slot11ModuleifInErrors              Counter64,
        slot11ModuleifInFcsErrorPkts        Counter64,
        slot11ModuleifInUnknownProtos       Counter64,	-- deprecated
        slot11ModuleifOutOctets             Counter64,
        slot11ModuleifOutUcastPkts          Counter64,
        slot11ModuleifOutNUcastPkts         Counter64,  -- deprecated
        slot11ModuleifOutDiscards           Counter64,
        slot11ModuleifOutErrors             Counter64,
        slot11ModuleifOutFcsErrorPkts       Counter64,
        slot11ModuleifOutQLen               Gauge32,    -- deprecated  
	    slot11ModuleifInpps   	    Counter64,
    	slot11ModuleifOutpps              Counter64,        
        slot11ModuleifRxPower                DisplayString,
        slot11ModuleifTxPower                DisplayString,
        slot11ModuleifSpecific              OBJECT IDENTIFIER
    }         

slot11ModuleifIndex OBJECT-TYPE
    SYNTAX      InterfaceIndex
    MAX-ACCESS  read-only
    STATUS      current
    DESCRIPTION
            "A unique value, greater than zero, for each interface.  It
            is recommended that values are assigned contiguously
            starting from 1.  The value for each interface sub-layer
            must remain constant at least from one re-initialization of
            the entity's network management system to the next re-
            initialization."
    ::= { slot11ModuleIfEntry 1 }
    
slot11ModuleIfId OBJECT-TYPE
    SYNTAX      DisplayString (SIZE (0..32))
    MAX-ACCESS  read-only
    STATUS      current
    DESCRIPTION
            "the value of module`s id"
    ::= { slot11ModuleIfEntry 2 }
    
slot11ModuleifDescr OBJECT-TYPE
    SYNTAX      DisplayString (SIZE (0..255))
    MAX-ACCESS  read-only
    STATUS      current
    DESCRIPTION
            "A textual string containing information about the
            interface.  This string should include the name of the
            manufacturer, the product name and the version of the
            interface hardware/software."
    ::= { slot11ModuleIfEntry 3 }
    
slot11ModuleifType OBJECT-TYPE
    SYNTAX      IANAifType
    MAX-ACCESS  read-only
    STATUS      current
    DESCRIPTION
            "The type of interface.  Additional values for ifType are
            assigned by the Internet Assigned Numbers Authority (IANA),
            through updating the syntax of the IANAifType textual
            convention."
    ::= { slot11ModuleIfEntry 4 }

slot11ModuleifMtu OBJECT-TYPE
    SYNTAX      Integer32(1..2147483647)
    MAX-ACCESS  read-only
    STATUS      current
    DESCRIPTION
            "The size of the largest packet which can be sent/received
            on the interface, specified in octets.  For interfaces that
            are used for transmitting network datagrams, this is the
            size of the largest network datagram that can be sent on the
            interface."
    ::= { slot11ModuleIfEntry 5 }

slot11ModuleifSpeed OBJECT-TYPE
    SYNTAX      Counter64
    MAX-ACCESS  read-only
    STATUS      current
    DESCRIPTION
            "An estimate of the interface's current bandwidth in bits
            per second.  For interfaces which do not vary in bandwidth
            or for those where no accurate estimation can be made, this
            object should contain the nominal bandwidth. For a sub-layer
            which has no concept of bandwidth, this object should be zero."
    ::= { slot11ModuleIfEntry 6 }

slot11ModuleifPhysAddress OBJECT-TYPE
    SYNTAX      PhysAddress
    MAX-ACCESS  read-only
    STATUS      current
    DESCRIPTION
            "The interface's address at its protocol sub-layer.  For
            example, for an 802.x interface, this object normally
            contains a MAC address.  The interface's media-specific MIB
            must define the bit and byte ordering and the format of the
            value of this object.  For interfaces which do not have such
            an address (e.g., a serial line), this object should contain
            an octet string of zero length."
    ::= { slot11ModuleIfEntry 7 }
    
slot11ModuleifAdminStatus OBJECT-TYPE
    SYNTAX  INTEGER {
                up(1),       -- ready to pass packets
                down(2),
                testing(3)   -- in some test mode
            }
    MAX-ACCESS  read-write
    STATUS      current
    DESCRIPTION
            "The desired state of the interface.  The testing(3) state
            indicates that no operational packets can be passed.  When a
            managed system initializes, all interfaces start with
            ifAdminStatus in the down(2) state.  As a result of either
            explicit management action or per configuration information
            retained by the managed system, ifAdminStatus is then
            changed to either the up(1) or testing(3) states (or remains
            in the down(2) state)."
    ::= { slot11ModuleIfEntry 8 }

slot11ModuleifOperStatus OBJECT-TYPE
    SYNTAX  INTEGER {
                up(1),        -- ready to pass packets
                down(2),
                testing(3),   -- in some test mode
                unknown(4),   -- status can not be determined
                              -- for some reason.
                dormant(5),
                notPresent(6),    -- some component is missing
                lowerLayerDown(7) -- down due to state of
                                  -- lower-layer interface(s)
            }
    MAX-ACCESS  read-only
    STATUS      current
    DESCRIPTION
            "The current operational state of the interface.  The
            testing(3) state indicates that no operational packets can
            be passed.  If ifAdminStatus is down(2) then ifOperStatus
            should be down(2).  If ifAdminStatus is changed to up(1)
            then ifOperStatus should change to up(1) if the interface is
            ready to transmit and receive network traffic; it should
            change to dormant(5) if the interface is waiting for
            external actions (such as a serial line waiting for an
            incoming connection); it should remain in the down(2) state
            if and only if there is a fault that prevents it from going
            to the up(1) state; it should remain in the notPresent(6)
            state if the interface has missing (typically, hardware)
            components."
    ::= { slot11ModuleIfEntry 9 }

slot11ModuleifLastChange OBJECT-TYPE
    SYNTAX      TimeTicks
    MAX-ACCESS  read-only
    STATUS      current
    DESCRIPTION
            "The value of sysUpTime at the time the interface entered
            its current operational state.  If the current state was
            entered prior to the last re-initialization of the local
            network management subsystem, then this object contains a
            zero value."
    ::= { slot11ModuleIfEntry 10 }

slot11ModuleifInKbits OBJECT-TYPE
    SYNTAX      Counter64
    MAX-ACCESS  read-only
    STATUS      current
    DESCRIPTION
            "The real time rate received on the interface, in Kbits
	    format.

            Discontinuities in the value of this counter can occur at
            re-initialization of the management system, and at other
            times as indicated by the value of
            ifCounterDiscontinuityTime."
    ::= { slot11ModuleIfEntry 11 }

slot11ModuleifOutKbits OBJECT-TYPE
    SYNTAX      Counter64
    MAX-ACCESS  read-only
    STATUS      current
    DESCRIPTION
            "The real time rate send on the interface, in Kbits
	    format.

            Discontinuities in the value of this counter can occur at
            re-initialization of the management system, and at other
            times as indicated by the value of
            ifCounterDiscontinuityTime."
    ::= { slot11ModuleIfEntry 12 }


slot11ModuleifInOctets OBJECT-TYPE
    SYNTAX      Counter64
    MAX-ACCESS  read-only
    STATUS      current
    DESCRIPTION
            "The total number of octets received on the interface,
            including framing characters.

            Discontinuities in the value of this counter can occur at
            re-initialization of the management system, and at other
            times as indicated by the value of
            ifCounterDiscontinuityTime."
    ::= { slot11ModuleIfEntry 13 }

slot11ModuleifInUcastPkts OBJECT-TYPE
    SYNTAX      Counter64
    MAX-ACCESS  read-only
    STATUS      current
    DESCRIPTION
            "The number of packets, delivered by this sub-layer to a
            higher (sub-)layer, which were not addressed to a multicast
            or broadcast address at this sub-layer.

            Discontinuities in the value of this counter can occur at
            re-initialization of the management system, and at other
            times as indicated by the value of
            ifCounterDiscontinuityTime."
    ::= { slot11ModuleIfEntry 14 }

slot11ModuleifInNUcastPkts OBJECT-TYPE
    SYNTAX  Counter64
    MAX-ACCESS  read-only
    STATUS      current
    DESCRIPTION
            "The number of packets, delivered by this sub-layer to a
            higher (sub-)layer, which were addressed to a multicast or
            broadcast address at this sub-layer.

            Discontinuities in the value of this counter can occur at
            re-initialization of the management system, and at other
            times as indicated by the value of
            ifCounterDiscontinuityTime.

            This object is deprecated in favour of ifInMulticastPkts and
            ifInBroadcastPkts."
    ::= { slot11ModuleIfEntry 15 }

slot11ModuleifInDiscards OBJECT-TYPE
    SYNTAX      Counter64
    MAX-ACCESS  read-only
    STATUS      current
    DESCRIPTION
            "The number of inbound packets which were chosen to be
            discarded even though no errors had been detected to prevent

            their being deliverable to a higher-layer protocol.  One
            possible reason for discarding such a packet could be to
            free up buffer space.

            Discontinuities in the value of this counter can occur at
            re-initialization of the management system, and at other
            times as indicated by the value of
            ifCounterDiscontinuityTime."
    ::= { slot11ModuleIfEntry 16 }

slot11ModuleifInErrors OBJECT-TYPE
    SYNTAX      Counter64
    MAX-ACCESS  read-only
    STATUS      current
    DESCRIPTION
            "For packet-oriented interfaces, the number of inbound
            packets that contained errors preventing them from being
            deliverable to a higher-layer protocol.  For character-
            oriented or fixed-length interfaces, the number of inbound
            transmission units that contained errors preventing them
            from being deliverable to a higher-layer protocol.

            Discontinuities in the value of this counter can occur at
            re-initialization of the management system, and at other
            times as indicated by the value of
            ifCounterDiscontinuityTime."
    ::= { slot11ModuleIfEntry 17 }

slot11ModuleifInFcsErrorPkts OBJECT-TYPE
    SYNTAX      Counter64
    MAX-ACCESS  read-only
    STATUS      current
    DESCRIPTION
            "FCS error pakets."
    ::= { slot11ModuleIfEntry 18 }

slot11ModuleifInUnknownProtos OBJECT-TYPE
    SYNTAX      Counter64
    MAX-ACCESS  read-only
    STATUS      current
    DESCRIPTION
            "For packet-oriented interfaces, the number of packets
            received via the interface which were discarded because of
            an unknown or unsupported protocol.  For character-oriented
            or fixed-length interfaces that support protocol
            multiplexing the number of transmission units received via
            the interface which were discarded because of an unknown or
            unsupported protocol.  For any interface that does not
            support protocol multiplexing, this counter will always be
            0.

            Discontinuities in the value of this counter can occur at
            re-initialization of the management system, and at other
            times as indicated by the value of
            ifCounterDiscontinuityTime."
    ::= { slot11ModuleIfEntry 19 }

slot11ModuleifOutOctets OBJECT-TYPE
    SYNTAX      Counter64
    MAX-ACCESS  read-only
    STATUS      current
    DESCRIPTION
            "The total number of octets transmitted out of the
            interface, including framing characters.

            Discontinuities in the value of this counter can occur at
            re-initialization of the management system, and at other
            times as indicated by the value of
            ifCounterDiscontinuityTime."
    ::= { slot11ModuleIfEntry 20 }

slot11ModuleifOutUcastPkts OBJECT-TYPE
    SYNTAX      Counter64
    MAX-ACCESS  read-only
    STATUS      current
    DESCRIPTION
            "The total number of packets that higher-level protocols
            requested be transmitted, and which were not addressed to a
            multicast or broadcast address at this sub-layer, including
            those that were discarded or not sent.

            Discontinuities in the value of this counter can occur at
            re-initialization of the management system, and at other
            times as indicated by the value of
            ifCounterDiscontinuityTime."
    ::= { slot11ModuleIfEntry 21 }

slot11ModuleifOutNUcastPkts OBJECT-TYPE
    SYNTAX      Counter64
    MAX-ACCESS  read-only
    STATUS      deprecated
    DESCRIPTION
            "The total number of packets that higher-level protocols
            requested be transmitted, and which were addressed to a
            multicast or broadcast address at this sub-layer, including
            those that were discarded or not sent.

            Discontinuities in the value of this counter can occur at
            re-initialization of the management system, and at other
            times as indicated by the value of
            ifCounterDiscontinuityTime.

            This object is deprecated in favour of ifOutMulticastPkts
            and ifOutBroadcastPkts."
    ::= { slot11ModuleIfEntry 22 }

slot11ModuleifOutDiscards OBJECT-TYPE
    SYNTAX      Counter64
    MAX-ACCESS  read-only
    STATUS      current
    DESCRIPTION
            "The number of outbound packets which were chosen to be
            discarded even though no errors had been detected to prevent
            their being transmitted.  One possible reason for discarding
            such a packet could be to free up buffer space.

            Discontinuities in the value of this counter can occur at
            re-initialization of the management system, and at other
            times as indicated by the value of
            ifCounterDiscontinuityTime."
    ::= { slot11ModuleIfEntry 23 }

slot11ModuleifOutErrors OBJECT-TYPE
    SYNTAX      Counter64
    MAX-ACCESS  read-only
    STATUS      current
    DESCRIPTION
            "For packet-oriented interfaces, the number of outbound
            packets that could not be transmitted because of errors.
            For character-oriented or fixed-length interfaces, the
            number of outbound transmission units that could not be
            transmitted because of errors.

            Discontinuities in the value of this counter can occur at
            re-initialization of the management system, and at other
            times as indicated by the value of
            ifCounterDiscontinuityTime."
    ::= { slot11ModuleIfEntry 24 }

slot11ModuleifOutFcsErrorPkts OBJECT-TYPE
    SYNTAX      Counter64
    MAX-ACCESS  read-only
    STATUS      current
    DESCRIPTION
            "FCS error pakets."
    ::= { slot11ModuleIfEntry 25 }

slot11ModuleifOutQLen OBJECT-TYPE
    SYNTAX      Gauge32
    MAX-ACCESS  read-only
    STATUS      deprecated
    DESCRIPTION
            "The length of the output packet queue (in packets)."
    ::= { slot11ModuleIfEntry 26 }

slot11ModuleifInpps OBJECT-TYPE
    SYNTAX      Counter64
    MAX-ACCESS  read-only
    STATUS      current
    DESCRIPTION
            "The real time rate received on the interface, in pps
	    format.

            Discontinuities in the value of this counter can occur at
            re-initialization of the management system, and at other
            times as indicated by the value of
            ifCounterDiscontinuityTime."
    ::= { slot11ModuleIfEntry 27 }

slot11ModuleifOutpps OBJECT-TYPE
    SYNTAX      Counter64
    MAX-ACCESS  read-only
    STATUS      current
    DESCRIPTION
            "The real time rate send on the interface, in pps
	    format.

            Discontinuities in the value of this counter can occur at
            re-initialization of the management system, and at other
            times as indicated by the value of
            ifCounterDiscontinuityTime."
    ::= { slot11ModuleIfEntry 28 }


slot11ModuleifRxPower OBJECT-TYPE
    SYNTAX      DisplayString (SIZE (0..255))
    MAX-ACCESS  read-only
    STATUS      current
    DESCRIPTION
            "the value of interface's received power, in dbm format."
    ::= { slot11ModuleIfEntry 29 }
    
slot11ModuleifTxPower OBJECT-TYPE
    SYNTAX      DisplayString (SIZE (0..255))
    MAX-ACCESS  read-only
    STATUS      current
    DESCRIPTION
            "the value of interface's send power, in dbm format."
    ::= { slot11ModuleIfEntry 30 }

slot11ModuleifSpecific OBJECT-TYPE
    SYNTAX      OBJECT IDENTIFIER
    MAX-ACCESS  read-only
    STATUS      deprecated
    DESCRIPTION
            "A reference to MIB definitions specific to the particular
            media being used to realize the interface.  It is

            recommended that this value point to an instance of a MIB
            object in the media-specific MIB, i.e., that this object
            have the semantics associated with the InstancePointer
            textual convention defined in RFC 2579.  In fact, it is
            recommended that the media-specific MIB specify what value
            ifSpecific should/can take for values of ifType.  If no MIB
            definitions specific to the particular media are available,
            the value should be set to the OBJECT IDENTIFIER { 0 0 }."
    ::= { slot11ModuleIfEntry 31 }  
    
-- slot 12 --

-- slot12Table --

slot12Table OBJECT-TYPE
    SYNTAX      SEQUENCE OF Slot12Entry
    MAX-ACCESS  not-accessible
    STATUS      current
    DESCRIPTION
            "A list of all slot12Type's utilization."
    ::= { slot12 1 }  

slot12Entry OBJECT-TYPE
    SYNTAX      Slot12Entry
    MAX-ACCESS  not-accessible
    STATUS      current
    DESCRIPTION
            "An entry contains a slot12's utilization."
    INDEX   { slot12Index }
    ::= { slot12Table 1 }

Slot12Entry ::=
    SEQUENCE {     
		slot12Index                       Integer32,
		slot12Type                        DisplayString,
		slot12Status                      DisplayString,		
		slot12Id                          Integer32
    }  

slot12Index OBJECT-TYPE
    SYNTAX      Integer32 (1..2147483647)
    MAX-ACCESS  not-accessible
    STATUS      current
    DESCRIPTION
            "A unique value, greater than zero, for each chassis`s slot12."
    ::= { slot12Entry 1 }

slot12Type OBJECT-TYPE
    SYNTAX      DisplayString (SIZE (0..255))
    MAX-ACCESS  read-only
    STATUS      current
    DESCRIPTION
            "the slot12Type of each chassis."
    ::= { slot12Entry 2 }

slot12Status OBJECT-TYPE
    SYNTAX      DisplayString (SIZE (0..255))
    MAX-ACCESS  read-only
    STATUS      current
    DESCRIPTION
            "A string to describe the board status." 
    ::= { slot12Entry 3 }   

slot12Id OBJECT-TYPE
    SYNTAX      Integer32
    MAX-ACCESS  read-only
    STATUS      current
    DESCRIPTION
            "slot id."
    ::= { slot12Entry 4 }

slot12Module OBJECT IDENTIFIER ::= { slot12 2 }

-- slot12ModuleTable --
slot12ModuleTable OBJECT-TYPE
    SYNTAX      SEQUENCE OF Slot12ModuleEntry
    MAX-ACCESS  not-accessible
    STATUS      current
    DESCRIPTION
            "A list of all slot12Module's utilization."
    ::= { slot12Module 1 }  

slot12ModuleEntry OBJECT-TYPE
    SYNTAX      Slot12ModuleEntry
    MAX-ACCESS  not-accessible
    STATUS      current
    DESCRIPTION
            "An entry contains a slot12Module's utilization."
    INDEX   { slot12ModuleIndex }
    ::= { slot12ModuleTable 1 }

Slot12ModuleEntry ::=
    SEQUENCE {     
		slot12ModuleIndex                       Integer32,
		slot12ModuleId                           DisplayString,  
		slot12ModuleIfNumber                     Integer32		
    } 

slot12ModuleIndex OBJECT-TYPE
    SYNTAX      Integer32 (1..2147483647)
    MAX-ACCESS  not-accessible
    STATUS      current
    DESCRIPTION
            "A unique value, greater than zero, for each chassis`s slot12."
    ::= { slot12ModuleEntry 1 }

slot12ModuleId OBJECT-TYPE
    SYNTAX      DisplayString (SIZE (0..32))
    MAX-ACCESS  read-only
    STATUS      current
    DESCRIPTION
            "the value of module`s id"
    ::= { slot12ModuleEntry 2 }
  
slot12ModuleIfNumber OBJECT-TYPE
    SYNTAX      Integer32(0..2147483647)
    MAX-ACCESS  read-only
    STATUS      current
    DESCRIPTION
            "The number of network interfaces (regardless of their
            current state) present on this system." 
    ::= { slot12ModuleEntry 3 } 
    
slot12ModuleIfTable OBJECT-TYPE
    SYNTAX      SEQUENCE OF Slot12ModuleIfEntry
    MAX-ACCESS  not-accessible
    STATUS      current
    DESCRIPTION
            "A list of interface entries.  The number of entries is
            given by the value of ifNumber."
    ::= { slot12Module 2 } 
    
slot12ModuleIfEntry OBJECT-TYPE
    SYNTAX      Slot12ModuleIfEntry
    MAX-ACCESS  not-accessible
    STATUS      current
    DESCRIPTION
            "An entry containing management information applicable to a
            particular interface."
    INDEX   { slot12ModuleifIndex }
    ::= { slot12ModuleIfTable 1 }
    
Slot12ModuleIfEntry ::=
    SEQUENCE {
        slot12ModuleifIndex                 InterfaceIndex,  
        slot12ModuleIfId                    DisplayString,  
        slot12ModuleifDescr                 DisplayString,           
        slot12ModuleifType                  IANAifType,   		
        slot12ModuleifMtu                   Integer32,                
        slot12ModuleifSpeed                 Counter64,               
        slot12ModuleifPhysAddress           PhysAddress,              
        slot12ModuleifAdminStatus           INTEGER,                  
        slot12ModuleifOperStatus            INTEGER,                  
        slot12ModuleifLastChange            TimeTicks,                
	slot12ModuleifInKbits   	    Counter64,
	slot12ModuleifOutKbits              Counter64,
        slot12ModuleifInOctets              Counter64,                
        slot12ModuleifInUcastPkts           Counter64,                
        slot12ModuleifInNUcastPkts          Counter64,   
        slot12ModuleifInDiscards            Counter64,
        slot12ModuleifInErrors              Counter64,
        slot12ModuleifInFcsErrorPkts        Counter64,
        slot12ModuleifInUnknownProtos       Counter64,	-- deprecated
        slot12ModuleifOutOctets             Counter64,
        slot12ModuleifOutUcastPkts          Counter64,
        slot12ModuleifOutNUcastPkts         Counter64,  -- deprecated
        slot12ModuleifOutDiscards           Counter64,
        slot12ModuleifOutErrors             Counter64,
        slot12ModuleifOutFcsErrorPkts       Counter64,
        slot12ModuleifOutQLen               Gauge32,    -- deprecated 
	    slot12ModuleifInpps   	    Counter64,
	    slot12ModuleifOutpps              Counter64,        
        slot12ModuleifRxPower                DisplayString,
        slot12ModuleifTxPower                DisplayString,
        slot12ModuleifSpecific              OBJECT IDENTIFIER
    }         

slot12ModuleifIndex OBJECT-TYPE
    SYNTAX      InterfaceIndex
    MAX-ACCESS  read-only
    STATUS      current
    DESCRIPTION
            "A unique value, greater than zero, for each interface.  It
            is recommended that values are assigned contiguously
            starting from 1.  The value for each interface sub-layer
            must remain constant at least from one re-initialization of
            the entity's network management system to the next re-
            initialization."
    ::= { slot12ModuleIfEntry 1 }
    
slot12ModuleIfId OBJECT-TYPE
    SYNTAX      DisplayString (SIZE (0..32))
    MAX-ACCESS  read-only
    STATUS      current
    DESCRIPTION
            "the value of module`s id"
    ::= { slot12ModuleIfEntry 2 }
    
slot12ModuleifDescr OBJECT-TYPE
    SYNTAX      DisplayString (SIZE (0..255))
    MAX-ACCESS  read-only
    STATUS      current
    DESCRIPTION
            "A textual string containing information about the
            interface.  This string should include the name of the
            manufacturer, the product name and the version of the
            interface hardware/software."
    ::= { slot12ModuleIfEntry 3 }
    
slot12ModuleifType OBJECT-TYPE
    SYNTAX      IANAifType
    MAX-ACCESS  read-only
    STATUS      current
    DESCRIPTION
            "The type of interface.  Additional values for ifType are
            assigned by the Internet Assigned Numbers Authority (IANA),
            through updating the syntax of the IANAifType textual
            convention."
    ::= { slot12ModuleIfEntry 4 }

slot12ModuleifMtu OBJECT-TYPE
    SYNTAX      Integer32(1..2147483647)
    MAX-ACCESS  read-only
    STATUS      current
    DESCRIPTION
            "The size of the largest packet which can be sent/received
            on the interface, specified in octets.  For interfaces that
            are used for transmitting network datagrams, this is the
            size of the largest network datagram that can be sent on the
            interface."
    ::= { slot12ModuleIfEntry 5 }

slot12ModuleifSpeed OBJECT-TYPE
    SYNTAX      Counter64
    MAX-ACCESS  read-only
    STATUS      current
    DESCRIPTION
            "An estimate of the interface's current bandwidth in bits
            per second.  For interfaces which do not vary in bandwidth
            or for those where no accurate estimation can be made, this
            object should contain the nominal bandwidth. For a sub-layer
            which has no concept of bandwidth, this object should be zero."
    ::= { slot12ModuleIfEntry 6 }

slot12ModuleifPhysAddress OBJECT-TYPE
    SYNTAX      PhysAddress
    MAX-ACCESS  read-only
    STATUS      current
    DESCRIPTION
            "The interface's address at its protocol sub-layer.  For
            example, for an 802.x interface, this object normally
            contains a MAC address.  The interface's media-specific MIB
            must define the bit and byte ordering and the format of the
            value of this object.  For interfaces which do not have such
            an address (e.g., a serial line), this object should contain
            an octet string of zero length."
    ::= { slot12ModuleIfEntry 7 }
    
slot12ModuleifAdminStatus OBJECT-TYPE
    SYNTAX  INTEGER {
                up(1),       -- ready to pass packets
                down(2),
                testing(3)   -- in some test mode
            }
    MAX-ACCESS  read-write
    STATUS      current
    DESCRIPTION
            "The desired state of the interface.  The testing(3) state
            indicates that no operational packets can be passed.  When a
            managed system initializes, all interfaces start with
            ifAdminStatus in the down(2) state.  As a result of either
            explicit management action or per configuration information
            retained by the managed system, ifAdminStatus is then
            changed to either the up(1) or testing(3) states (or remains
            in the down(2) state)."
    ::= { slot12ModuleIfEntry 8 }

slot12ModuleifOperStatus OBJECT-TYPE
    SYNTAX  INTEGER {
                up(1),        -- ready to pass packets
                down(2),
                testing(3),   -- in some test mode
                unknown(4),   -- status can not be determined
                              -- for some reason.
                dormant(5),
                notPresent(6),    -- some component is missing
                lowerLayerDown(7) -- down due to state of
                                  -- lower-layer interface(s)
            }
    MAX-ACCESS  read-only
    STATUS      current
    DESCRIPTION
            "The current operational state of the interface.  The
            testing(3) state indicates that no operational packets can
            be passed.  If ifAdminStatus is down(2) then ifOperStatus
            should be down(2).  If ifAdminStatus is changed to up(1)
            then ifOperStatus should change to up(1) if the interface is
            ready to transmit and receive network traffic; it should
            change to dormant(5) if the interface is waiting for
            external actions (such as a serial line waiting for an
            incoming connection); it should remain in the down(2) state
            if and only if there is a fault that prevents it from going
            to the up(1) state; it should remain in the notPresent(6)
            state if the interface has missing (typically, hardware)
            components."
    ::= { slot12ModuleIfEntry 9 }

slot12ModuleifLastChange OBJECT-TYPE
    SYNTAX      TimeTicks
    MAX-ACCESS  read-only
    STATUS      current
    DESCRIPTION
            "The value of sysUpTime at the time the interface entered
            its current operational state.  If the current state was
            entered prior to the last re-initialization of the local
            network management subsystem, then this object contains a
            zero value."
    ::= { slot12ModuleIfEntry 10 }

slot12ModuleifInKbits OBJECT-TYPE
    SYNTAX      Counter64
    MAX-ACCESS  read-only
    STATUS      current
    DESCRIPTION
            "The real time rate received on the interface, in Kbits
	    format.

            Discontinuities in the value of this counter can occur at
            re-initialization of the management system, and at other
            times as indicated by the value of
            ifCounterDiscontinuityTime."
    ::= { slot12ModuleIfEntry 11 }

slot12ModuleifOutKbits OBJECT-TYPE
    SYNTAX      Counter64
    MAX-ACCESS  read-only
    STATUS      current
    DESCRIPTION
            "The real time rate send on the interface, in Kbits
	    format.

            Discontinuities in the value of this counter can occur at
            re-initialization of the management system, and at other
            times as indicated by the value of
            ifCounterDiscontinuityTime."
    ::= { slot12ModuleIfEntry 12 }

slot12ModuleifInOctets OBJECT-TYPE
    SYNTAX      Counter64
    MAX-ACCESS  read-only
    STATUS      current
    DESCRIPTION
            "The total number of octets received on the interface,
            including framing characters.

            Discontinuities in the value of this counter can occur at
            re-initialization of the management system, and at other
            times as indicated by the value of
            ifCounterDiscontinuityTime."
    ::= { slot12ModuleIfEntry 13 }

slot12ModuleifInUcastPkts OBJECT-TYPE
    SYNTAX      Counter64
    MAX-ACCESS  read-only
    STATUS      current
    DESCRIPTION
            "The number of packets, delivered by this sub-layer to a
            higher (sub-)layer, which were not addressed to a multicast
            or broadcast address at this sub-layer.

            Discontinuities in the value of this counter can occur at
            re-initialization of the management system, and at other
            times as indicated by the value of
            ifCounterDiscontinuityTime."
    ::= { slot12ModuleIfEntry 14 }

slot12ModuleifInNUcastPkts OBJECT-TYPE
    SYNTAX  Counter64
    MAX-ACCESS  read-only
    STATUS      current
    DESCRIPTION
            "The number of packets, delivered by this sub-layer to a
            higher (sub-)layer, which were addressed to a multicast or
            broadcast address at this sub-layer.

            Discontinuities in the value of this counter can occur at
            re-initialization of the management system, and at other
            times as indicated by the value of
            ifCounterDiscontinuityTime.

            This object is deprecated in favour of ifInMulticastPkts and
            ifInBroadcastPkts."
    ::= { slot12ModuleIfEntry 15 }

slot12ModuleifInDiscards OBJECT-TYPE
    SYNTAX      Counter64
    MAX-ACCESS  read-only
    STATUS      current
    DESCRIPTION
            "The number of inbound packets which were chosen to be
            discarded even though no errors had been detected to prevent

            their being deliverable to a higher-layer protocol.  One
            possible reason for discarding such a packet could be to
            free up buffer space.

            Discontinuities in the value of this counter can occur at
            re-initialization of the management system, and at other
            times as indicated by the value of
            ifCounterDiscontinuityTime."
    ::= { slot12ModuleIfEntry 16 }

slot12ModuleifInErrors OBJECT-TYPE
    SYNTAX      Counter64
    MAX-ACCESS  read-only
    STATUS      current
    DESCRIPTION
            "For packet-oriented interfaces, the number of inbound
            packets that contained errors preventing them from being
            deliverable to a higher-layer protocol.  For character-
            oriented or fixed-length interfaces, the number of inbound
            transmission units that contained errors preventing them
            from being deliverable to a higher-layer protocol.

            Discontinuities in the value of this counter can occur at
            re-initialization of the management system, and at other
            times as indicated by the value of
            ifCounterDiscontinuityTime."
    ::= { slot12ModuleIfEntry 17 }

slot12ModuleifInFcsErrorPkts OBJECT-TYPE
    SYNTAX      Counter64
    MAX-ACCESS  read-only
    STATUS      current
    DESCRIPTION
            "FCS error pakets."
    ::= { slot12ModuleIfEntry 18 }

slot12ModuleifInUnknownProtos OBJECT-TYPE
    SYNTAX      Counter64
    MAX-ACCESS  read-only
    STATUS      current
    DESCRIPTION
            "For packet-oriented interfaces, the number of packets
            received via the interface which were discarded because of
            an unknown or unsupported protocol.  For character-oriented
            or fixed-length interfaces that support protocol
            multiplexing the number of transmission units received via
            the interface which were discarded because of an unknown or
            unsupported protocol.  For any interface that does not
            support protocol multiplexing, this counter will always be
            0.

            Discontinuities in the value of this counter can occur at
            re-initialization of the management system, and at other
            times as indicated by the value of
            ifCounterDiscontinuityTime."
    ::= { slot12ModuleIfEntry 19 }

slot12ModuleifOutOctets OBJECT-TYPE
    SYNTAX      Counter64
    MAX-ACCESS  read-only
    STATUS      current
    DESCRIPTION
            "The total number of octets transmitted out of the
            interface, including framing characters.

            Discontinuities in the value of this counter can occur at
            re-initialization of the management system, and at other
            times as indicated by the value of
            ifCounterDiscontinuityTime."
    ::= { slot12ModuleIfEntry 20 }

slot12ModuleifOutUcastPkts OBJECT-TYPE
    SYNTAX      Counter64
    MAX-ACCESS  read-only
    STATUS      current
    DESCRIPTION
            "The total number of packets that higher-level protocols
            requested be transmitted, and which were not addressed to a
            multicast or broadcast address at this sub-layer, including
            those that were discarded or not sent.

            Discontinuities in the value of this counter can occur at
            re-initialization of the management system, and at other
            times as indicated by the value of
            ifCounterDiscontinuityTime."
    ::= { slot12ModuleIfEntry 21 }

slot12ModuleifOutNUcastPkts OBJECT-TYPE
    SYNTAX      Counter64
    MAX-ACCESS  read-only
    STATUS      deprecated
    DESCRIPTION
            "The total number of packets that higher-level protocols
            requested be transmitted, and which were addressed to a
            multicast or broadcast address at this sub-layer, including
            those that were discarded or not sent.

            Discontinuities in the value of this counter can occur at
            re-initialization of the management system, and at other
            times as indicated by the value of
            ifCounterDiscontinuityTime.

            This object is deprecated in favour of ifOutMulticastPkts
            and ifOutBroadcastPkts."
    ::= { slot12ModuleIfEntry 22 }

slot12ModuleifOutDiscards OBJECT-TYPE
    SYNTAX      Counter64
    MAX-ACCESS  read-only
    STATUS      current
    DESCRIPTION
            "The number of outbound packets which were chosen to be
            discarded even though no errors had been detected to prevent
            their being transmitted.  One possible reason for discarding
            such a packet could be to free up buffer space.

            Discontinuities in the value of this counter can occur at
            re-initialization of the management system, and at other
            times as indicated by the value of
            ifCounterDiscontinuityTime."
    ::= { slot12ModuleIfEntry 23 }

slot12ModuleifOutErrors OBJECT-TYPE
    SYNTAX      Counter64
    MAX-ACCESS  read-only
    STATUS      current
    DESCRIPTION
            "For packet-oriented interfaces, the number of outbound
            packets that could not be transmitted because of errors.
            For character-oriented or fixed-length interfaces, the
            number of outbound transmission units that could not be
            transmitted because of errors.

            Discontinuities in the value of this counter can occur at
            re-initialization of the management system, and at other
            times as indicated by the value of
            ifCounterDiscontinuityTime."
    ::= { slot12ModuleIfEntry 24 }

slot12ModuleifOutFcsErrorPkts OBJECT-TYPE
    SYNTAX      Counter64
    MAX-ACCESS  read-only
    STATUS      current
    DESCRIPTION
            "FCS error pakets."
    ::= { slot12ModuleIfEntry 25 }

slot12ModuleifOutQLen OBJECT-TYPE
    SYNTAX      Gauge32
    MAX-ACCESS  read-only
    STATUS      deprecated
    DESCRIPTION
            "The length of the output packet queue (in packets)."
    ::= { slot12ModuleIfEntry 26 }

slot12ModuleifInpps OBJECT-TYPE
    SYNTAX      Counter64
    MAX-ACCESS  read-only
    STATUS      current
    DESCRIPTION
            "The real time rate received on the interface, in pps
	    format.

            Discontinuities in the value of this counter can occur at
            re-initialization of the management system, and at other
            times as indicated by the value of
            ifCounterDiscontinuityTime."
    ::= { slot12ModuleIfEntry 27 }

slot12ModuleifOutpps OBJECT-TYPE
    SYNTAX      Counter64
    MAX-ACCESS  read-only
    STATUS      current
    DESCRIPTION
            "The real time rate send on the interface, in pps
	    format.

            Discontinuities in the value of this counter can occur at
            re-initialization of the management system, and at other
            times as indicated by the value of
            ifCounterDiscontinuityTime."
    ::= { slot12ModuleIfEntry 28 }

slot12ModuleifRxPower OBJECT-TYPE
    SYNTAX      DisplayString (SIZE (0..255))
    MAX-ACCESS  read-only
    STATUS      current
    DESCRIPTION
            "the value of interface's received power, in dbm format."
    ::= { slot12ModuleIfEntry 29 }
    
slot12ModuleifTxPower OBJECT-TYPE
    SYNTAX      DisplayString (SIZE (0..255))
    MAX-ACCESS  read-only
    STATUS      current
    DESCRIPTION
            "the value of interface's send power, in dbm format."
    ::= { slot12ModuleIfEntry 30 }

slot12ModuleifSpecific OBJECT-TYPE
    SYNTAX      OBJECT IDENTIFIER
    MAX-ACCESS  read-only
    STATUS      deprecated
    DESCRIPTION
            "A reference to MIB definitions specific to the particular
            media being used to realize the interface.  It is

            recommended that this value point to an instance of a MIB
            object in the media-specific MIB, i.e., that this object
            have the semantics associated with the InstancePointer
            textual convention defined in RFC 2579.  In fact, it is
            recommended that the media-specific MIB specify what value
            ifSpecific should/can take for values of ifType.  If no MIB
            definitions specific to the particular media are available,
            the value should be set to the OBJECT IDENTIFIER { 0 0 }."
    ::= { slot12ModuleIfEntry 31 }  
    
-- slot 13 --

-- slot13Table --

slot13Table OBJECT-TYPE
    SYNTAX      SEQUENCE OF Slot13Entry
    MAX-ACCESS  not-accessible
    STATUS      current
    DESCRIPTION
            "A list of all slot13Type's utilization."
    ::= { slot13 1 }  

slot13Entry OBJECT-TYPE
    SYNTAX      Slot13Entry
    MAX-ACCESS  not-accessible
    STATUS      current
    DESCRIPTION
            "An entry contains a slot13's utilization."
    INDEX   { slot13Index }
    ::= { slot13Table 1 }

Slot13Entry ::=
    SEQUENCE {     
		slot13Index                       Integer32,
		slot13Type                        DisplayString,
		slot13Status                      DisplayString,		
		slot13Id                          Integer32
    }  

slot13Index OBJECT-TYPE
    SYNTAX      Integer32 (1..2147483647)
    MAX-ACCESS  not-accessible
    STATUS      current
    DESCRIPTION
            "A unique value, greater than zero, for each chassis`s slot13."
    ::= { slot13Entry 1 }

slot13Type OBJECT-TYPE
    SYNTAX      DisplayString (SIZE (0..255))
    MAX-ACCESS  read-only
    STATUS      current
    DESCRIPTION
            "the slot13Type of each chassis."
    ::= { slot13Entry 2 }

slot13Status OBJECT-TYPE
    SYNTAX      DisplayString (SIZE (0..255))
    MAX-ACCESS  read-only
    STATUS      current
    DESCRIPTION
            "A string to describe the board status." 
    ::= { slot13Entry 3 }   

slot13Id OBJECT-TYPE
    SYNTAX      Integer32
    MAX-ACCESS  read-only
    STATUS      current
    DESCRIPTION
            "slot id."
    ::= { slot13Entry 4 }

slot13Module OBJECT IDENTIFIER ::= { slot13 2 }

-- slot13ModuleTable --
slot13ModuleTable OBJECT-TYPE
    SYNTAX      SEQUENCE OF Slot13ModuleEntry
    MAX-ACCESS  not-accessible
    STATUS      current
    DESCRIPTION
            "A list of all slot13Module's utilization."
    ::= { slot13Module 1 }  

slot13ModuleEntry OBJECT-TYPE
    SYNTAX      Slot13ModuleEntry
    MAX-ACCESS  not-accessible
    STATUS      current
    DESCRIPTION
            "An entry contains a slot13Module's utilization."
    INDEX   { slot13ModuleIndex }
    ::= { slot13ModuleTable 1 }

Slot13ModuleEntry ::=
    SEQUENCE {     
		slot13ModuleIndex                       Integer32,
		slot13ModuleId                           DisplayString,  
		slot13ModuleIfNumber                     Integer32		
    } 

slot13ModuleIndex OBJECT-TYPE
    SYNTAX      Integer32 (1..2147483647)
    MAX-ACCESS  not-accessible
    STATUS      current
    DESCRIPTION
            "A unique value, greater than zero, for each chassis`s slot13."
    ::= { slot13ModuleEntry 1 }

slot13ModuleId OBJECT-TYPE
    SYNTAX      DisplayString (SIZE (0..32))
    MAX-ACCESS  read-only
    STATUS      current
    DESCRIPTION
            "the value of module`s id"
    ::= { slot13ModuleEntry 2 }
  
slot13ModuleIfNumber OBJECT-TYPE
    SYNTAX      Integer32(0..2147483647)
    MAX-ACCESS  read-only
    STATUS      current
    DESCRIPTION
            "The number of network interfaces (regardless of their
            current state) present on this system." 
    ::= { slot13ModuleEntry 3 } 
    
slot13ModuleIfTable OBJECT-TYPE
    SYNTAX      SEQUENCE OF Slot13ModuleIfEntry
    MAX-ACCESS  not-accessible
    STATUS      current
    DESCRIPTION
            "A list of interface entries.  The number of entries is
            given by the value of ifNumber."
    ::= { slot13Module 2 } 
    
slot13ModuleIfEntry OBJECT-TYPE
    SYNTAX      Slot13ModuleIfEntry
    MAX-ACCESS  not-accessible
    STATUS      current
    DESCRIPTION
            "An entry containing management information applicable to a
            particular interface."
    INDEX   { slot13ModuleifIndex }
    ::= { slot13ModuleIfTable 1 }
    
Slot13ModuleIfEntry ::=
    SEQUENCE {
        slot13ModuleifIndex                 InterfaceIndex,  
        slot13ModuleIfId                    DisplayString,  
        slot13ModuleifDescr                 DisplayString,           
        slot13ModuleifType                  IANAifType,   		
        slot13ModuleifMtu                   Integer32,                
        slot13ModuleifSpeed                 Counter64,               
        slot13ModuleifPhysAddress           PhysAddress,              
        slot13ModuleifAdminStatus           INTEGER,                  
        slot13ModuleifOperStatus            INTEGER,                  
        slot13ModuleifLastChange            TimeTicks,                
	slot13ModuleifInKbits   	    Counter64,
	slot13ModuleifOutKbits              Counter64,
        slot13ModuleifInOctets              Counter64,                
        slot13ModuleifInUcastPkts           Counter64,                
        slot13ModuleifInNUcastPkts          Counter64, 
        slot13ModuleifInDiscards            Counter64,
        slot13ModuleifInErrors              Counter64,
        slot13ModuleifInFcsErrorPkts        Counter64,
        slot13ModuleifInUnknownProtos       Counter64,	-- deprecated
        slot13ModuleifOutOctets             Counter64,
        slot13ModuleifOutUcastPkts          Counter64,
        slot13ModuleifOutNUcastPkts         Counter64,  -- deprecated
        slot13ModuleifOutDiscards           Counter64,
        slot13ModuleifOutErrors             Counter64,
        slot13ModuleifOutFcsErrorPkts       Counter64,
        slot13ModuleifOutQLen               Gauge32,    -- deprecated  
	    slot13ModuleifInpps   	    Counter64,
	    slot13ModuleifOutpps              Counter64,        
        slot13ModuleifRxPower                DisplayString,
        slot13ModuleifTxPower                DisplayString,
        slot13ModuleifSpecific              OBJECT IDENTIFIER
    }         

slot13ModuleifIndex OBJECT-TYPE
    SYNTAX      InterfaceIndex
    MAX-ACCESS  read-only
    STATUS      current
    DESCRIPTION
            "A unique value, greater than zero, for each interface.  It
            is recommended that values are assigned contiguously
            starting from 1.  The value for each interface sub-layer
            must remain constant at least from one re-initialization of
            the entity's network management system to the next re-
            initialization."
    ::= { slot13ModuleIfEntry 1 }
    
slot13ModuleIfId OBJECT-TYPE
    SYNTAX      DisplayString (SIZE (0..32))
    MAX-ACCESS  read-only
    STATUS      current
    DESCRIPTION
            "the value of module`s id"
    ::= { slot13ModuleIfEntry 2 }
    
slot13ModuleifDescr OBJECT-TYPE
    SYNTAX      DisplayString (SIZE (0..255))
    MAX-ACCESS  read-only
    STATUS      current
    DESCRIPTION
            "A textual string containing information about the
            interface.  This string should include the name of the
            manufacturer, the product name and the version of the
            interface hardware/software."
    ::= { slot13ModuleIfEntry 3 }
    
slot13ModuleifType OBJECT-TYPE
    SYNTAX      IANAifType
    MAX-ACCESS  read-only
    STATUS      current
    DESCRIPTION
            "The type of interface.  Additional values for ifType are
            assigned by the Internet Assigned Numbers Authority (IANA),
            through updating the syntax of the IANAifType textual
            convention."
    ::= { slot13ModuleIfEntry 4 }

slot13ModuleifMtu OBJECT-TYPE
    SYNTAX      Integer32(1..2147483647)
    MAX-ACCESS  read-only
    STATUS      current
    DESCRIPTION
            "The size of the largest packet which can be sent/received
            on the interface, specified in octets.  For interfaces that
            are used for transmitting network datagrams, this is the
            size of the largest network datagram that can be sent on the
            interface."
    ::= { slot13ModuleIfEntry 5 }

slot13ModuleifSpeed OBJECT-TYPE
    SYNTAX      Counter64
    MAX-ACCESS  read-only
    STATUS      current
    DESCRIPTION
            "An estimate of the interface's current bandwidth in bits
            per second.  For interfaces which do not vary in bandwidth
            or for those where no accurate estimation can be made, this
            object should contain the nominal bandwidth. For a sub-layer
            which has no concept of bandwidth, this object should be zero."
    ::= { slot13ModuleIfEntry 6 }

slot13ModuleifPhysAddress OBJECT-TYPE
    SYNTAX      PhysAddress
    MAX-ACCESS  read-only
    STATUS      current
    DESCRIPTION
            "The interface's address at its protocol sub-layer.  For
            example, for an 802.x interface, this object normally
            contains a MAC address.  The interface's media-specific MIB
            must define the bit and byte ordering and the format of the
            value of this object.  For interfaces which do not have such
            an address (e.g., a serial line), this object should contain
            an octet string of zero length."
    ::= { slot13ModuleIfEntry 7 }
    
slot13ModuleifAdminStatus OBJECT-TYPE
    SYNTAX  INTEGER {
                up(1),       -- ready to pass packets
                down(2),
                testing(3)   -- in some test mode
            }
    MAX-ACCESS  read-write
    STATUS      current
    DESCRIPTION
            "The desired state of the interface.  The testing(3) state
            indicates that no operational packets can be passed.  When a
            managed system initializes, all interfaces start with
            ifAdminStatus in the down(2) state.  As a result of either
            explicit management action or per configuration information
            retained by the managed system, ifAdminStatus is then
            changed to either the up(1) or testing(3) states (or remains
            in the down(2) state)."
    ::= { slot13ModuleIfEntry 8 }

slot13ModuleifOperStatus OBJECT-TYPE
    SYNTAX  INTEGER {
                up(1),        -- ready to pass packets
                down(2),
                testing(3),   -- in some test mode
                unknown(4),   -- status can not be determined
                              -- for some reason.
                dormant(5),
                notPresent(6),    -- some component is missing
                lowerLayerDown(7) -- down due to state of
                                  -- lower-layer interface(s)
            }
    MAX-ACCESS  read-only
    STATUS      current
    DESCRIPTION
            "The current operational state of the interface.  The
            testing(3) state indicates that no operational packets can
            be passed.  If ifAdminStatus is down(2) then ifOperStatus
            should be down(2).  If ifAdminStatus is changed to up(1)
            then ifOperStatus should change to up(1) if the interface is
            ready to transmit and receive network traffic; it should
            change to dormant(5) if the interface is waiting for
            external actions (such as a serial line waiting for an
            incoming connection); it should remain in the down(2) state
            if and only if there is a fault that prevents it from going
            to the up(1) state; it should remain in the notPresent(6)
            state if the interface has missing (typically, hardware)
            components."
    ::= { slot13ModuleIfEntry 9 }

slot13ModuleifLastChange OBJECT-TYPE
    SYNTAX      TimeTicks
    MAX-ACCESS  read-only
    STATUS      current
    DESCRIPTION
            "The value of sysUpTime at the time the interface entered
            its current operational state.  If the current state was
            entered prior to the last re-initialization of the local
            network management subsystem, then this object contains a
            zero value."
    ::= { slot13ModuleIfEntry 10 }

slot13ModuleifInKbits OBJECT-TYPE
    SYNTAX      Counter64
    MAX-ACCESS  read-only
    STATUS      current
    DESCRIPTION
            "The real time rate received on the interface, in Kbits
	    format.

            Discontinuities in the value of this counter can occur at
            re-initialization of the management system, and at other
            times as indicated by the value of
            ifCounterDiscontinuityTime."
    ::= { slot13ModuleIfEntry 11 }

slot13ModuleifOutKbits OBJECT-TYPE
    SYNTAX      Counter64
    MAX-ACCESS  read-only
    STATUS      current
    DESCRIPTION
            "The real time rate send on the interface, in Kbits
	    format.

            Discontinuities in the value of this counter can occur at
            re-initialization of the management system, and at other
            times as indicated by the value of
            ifCounterDiscontinuityTime."
    ::= { slot13ModuleIfEntry 12 }


slot13ModuleifInOctets OBJECT-TYPE
    SYNTAX      Counter64
    MAX-ACCESS  read-only
    STATUS      current
    DESCRIPTION
            "The total number of octets received on the interface,
            including framing characters.

            Discontinuities in the value of this counter can occur at
            re-initialization of the management system, and at other
            times as indicated by the value of
            ifCounterDiscontinuityTime."
    ::= { slot13ModuleIfEntry 13 }

slot13ModuleifInUcastPkts OBJECT-TYPE
    SYNTAX      Counter64
    MAX-ACCESS  read-only
    STATUS      current
    DESCRIPTION
            "The number of packets, delivered by this sub-layer to a
            higher (sub-)layer, which were not addressed to a multicast
            or broadcast address at this sub-layer.

            Discontinuities in the value of this counter can occur at
            re-initialization of the management system, and at other
            times as indicated by the value of
            ifCounterDiscontinuityTime."
    ::= { slot13ModuleIfEntry 14 }

slot13ModuleifInNUcastPkts OBJECT-TYPE
    SYNTAX  Counter64
    MAX-ACCESS  read-only
    STATUS      current
    DESCRIPTION
            "The number of packets, delivered by this sub-layer to a
            higher (sub-)layer, which were addressed to a multicast or
            broadcast address at this sub-layer.

            Discontinuities in the value of this counter can occur at
            re-initialization of the management system, and at other
            times as indicated by the value of
            ifCounterDiscontinuityTime.

            This object is deprecated in favour of ifInMulticastPkts and
            ifInBroadcastPkts."
    ::= { slot13ModuleIfEntry 15 }

slot13ModuleifInDiscards OBJECT-TYPE
    SYNTAX      Counter64
    MAX-ACCESS  read-only
    STATUS      current
    DESCRIPTION
            "The number of inbound packets which were chosen to be
            discarded even though no errors had been detected to prevent

            their being deliverable to a higher-layer protocol.  One
            possible reason for discarding such a packet could be to
            free up buffer space.

            Discontinuities in the value of this counter can occur at
            re-initialization of the management system, and at other
            times as indicated by the value of
            ifCounterDiscontinuityTime."
    ::= { slot13ModuleIfEntry 16 }

slot13ModuleifInErrors OBJECT-TYPE
    SYNTAX      Counter64
    MAX-ACCESS  read-only
    STATUS      current
    DESCRIPTION
            "For packet-oriented interfaces, the number of inbound
            packets that contained errors preventing them from being
            deliverable to a higher-layer protocol.  For character-
            oriented or fixed-length interfaces, the number of inbound
            transmission units that contained errors preventing them
            from being deliverable to a higher-layer protocol.

            Discontinuities in the value of this counter can occur at
            re-initialization of the management system, and at other
            times as indicated by the value of
            ifCounterDiscontinuityTime."
    ::= { slot13ModuleIfEntry 17 }

slot13ModuleifInFcsErrorPkts OBJECT-TYPE
    SYNTAX      Counter64
    MAX-ACCESS  read-only
    STATUS      current
    DESCRIPTION
            "FCS error pakets."
    ::= { slot13ModuleIfEntry 18 }

slot13ModuleifInUnknownProtos OBJECT-TYPE
    SYNTAX      Counter64
    MAX-ACCESS  read-only
    STATUS      current
    DESCRIPTION
            "For packet-oriented interfaces, the number of packets
            received via the interface which were discarded because of
            an unknown or unsupported protocol.  For character-oriented
            or fixed-length interfaces that support protocol
            multiplexing the number of transmission units received via
            the interface which were discarded because of an unknown or
            unsupported protocol.  For any interface that does not
            support protocol multiplexing, this counter will always be
            0.

            Discontinuities in the value of this counter can occur at
            re-initialization of the management system, and at other
            times as indicated by the value of
            ifCounterDiscontinuityTime."
    ::= { slot13ModuleIfEntry 19 }

slot13ModuleifOutOctets OBJECT-TYPE
    SYNTAX      Counter64
    MAX-ACCESS  read-only
    STATUS      current
    DESCRIPTION
            "The total number of octets transmitted out of the
            interface, including framing characters.

            Discontinuities in the value of this counter can occur at
            re-initialization of the management system, and at other
            times as indicated by the value of
            ifCounterDiscontinuityTime."
    ::= { slot13ModuleIfEntry 20 }

slot13ModuleifOutUcastPkts OBJECT-TYPE
    SYNTAX      Counter64
    MAX-ACCESS  read-only
    STATUS      current
    DESCRIPTION
            "The total number of packets that higher-level protocols
            requested be transmitted, and which were not addressed to a
            multicast or broadcast address at this sub-layer, including
            those that were discarded or not sent.

            Discontinuities in the value of this counter can occur at
            re-initialization of the management system, and at other
            times as indicated by the value of
            ifCounterDiscontinuityTime."
    ::= { slot13ModuleIfEntry 21 }

slot13ModuleifOutNUcastPkts OBJECT-TYPE
    SYNTAX      Counter64
    MAX-ACCESS  read-only
    STATUS      deprecated
    DESCRIPTION
            "The total number of packets that higher-level protocols
            requested be transmitted, and which were addressed to a
            multicast or broadcast address at this sub-layer, including
            those that were discarded or not sent.

            Discontinuities in the value of this counter can occur at
            re-initialization of the management system, and at other
            times as indicated by the value of
            ifCounterDiscontinuityTime.

            This object is deprecated in favour of ifOutMulticastPkts
            and ifOutBroadcastPkts."
    ::= { slot13ModuleIfEntry 22 }

slot13ModuleifOutDiscards OBJECT-TYPE
    SYNTAX      Counter64
    MAX-ACCESS  read-only
    STATUS      current
    DESCRIPTION
            "The number of outbound packets which were chosen to be
            discarded even though no errors had been detected to prevent
            their being transmitted.  One possible reason for discarding
            such a packet could be to free up buffer space.

            Discontinuities in the value of this counter can occur at
            re-initialization of the management system, and at other
            times as indicated by the value of
            ifCounterDiscontinuityTime."
    ::= { slot13ModuleIfEntry 23 }

slot13ModuleifOutErrors OBJECT-TYPE
    SYNTAX      Counter64
    MAX-ACCESS  read-only
    STATUS      current
    DESCRIPTION
            "For packet-oriented interfaces, the number of outbound
            packets that could not be transmitted because of errors.
            For character-oriented or fixed-length interfaces, the
            number of outbound transmission units that could not be
            transmitted because of errors.

            Discontinuities in the value of this counter can occur at
            re-initialization of the management system, and at other
            times as indicated by the value of
            ifCounterDiscontinuityTime."
    ::= { slot13ModuleIfEntry 24 }

slot13ModuleifOutFcsErrorPkts OBJECT-TYPE
    SYNTAX      Counter64
    MAX-ACCESS  read-only
    STATUS      current
    DESCRIPTION
            "FCS error pakets."
    ::= { slot13ModuleIfEntry 25 }

slot13ModuleifOutQLen OBJECT-TYPE
    SYNTAX      Gauge32
    MAX-ACCESS  read-only
    STATUS      deprecated
    DESCRIPTION
            "The length of the output packet queue (in packets)."
    ::= { slot13ModuleIfEntry 26 }

slot13ModuleifInpps OBJECT-TYPE
    SYNTAX      Counter64
    MAX-ACCESS  read-only
    STATUS      current
    DESCRIPTION
            "The real time rate received on the interface, in pps
	    format.

            Discontinuities in the value of this counter can occur at
            re-initialization of the management system, and at other
            times as indicated by the value of
            ifCounterDiscontinuityTime."
    ::= { slot13ModuleIfEntry 27 }

slot13ModuleifOutpps OBJECT-TYPE
    SYNTAX      Counter64
    MAX-ACCESS  read-only
    STATUS      current
    DESCRIPTION
            "The real time rate send on the interface, in pps
	    format.

            Discontinuities in the value of this counter can occur at
            re-initialization of the management system, and at other
            times as indicated by the value of
            ifCounterDiscontinuityTime."
    ::= { slot13ModuleIfEntry 28 }

slot13ModuleifRxPower OBJECT-TYPE
    SYNTAX      DisplayString (SIZE (0..255))
    MAX-ACCESS  read-only
    STATUS      current
    DESCRIPTION
            "the value of interface's received power, in dbm format."
    ::= { slot13ModuleIfEntry 29 }
    
slot13ModuleifTxPower OBJECT-TYPE
    SYNTAX      DisplayString (SIZE (0..255))
    MAX-ACCESS  read-only
    STATUS      current
    DESCRIPTION
            "the value of interface's send power, in dbm format."
    ::= { slot13ModuleIfEntry 30 }

slot13ModuleifSpecific OBJECT-TYPE
    SYNTAX      OBJECT IDENTIFIER
    MAX-ACCESS  read-only
    STATUS      deprecated
    DESCRIPTION
            "A reference to MIB definitions specific to the particular
            media being used to realize the interface.  It is

            recommended that this value point to an instance of a MIB
            object in the media-specific MIB, i.e., that this object
            have the semantics associated with the InstancePointer
            textual convention defined in RFC 2579.  In fact, it is
            recommended that the media-specific MIB specify what value
            ifSpecific should/can take for values of ifType.  If no MIB
            definitions specific to the particular media are available,
            the value should be set to the OBJECT IDENTIFIER { 0 0 }."
    ::= { slot13ModuleIfEntry 31 }  
    
-- slot 14 --

-- slot14Table --

slot14Table OBJECT-TYPE
    SYNTAX      SEQUENCE OF Slot14Entry
    MAX-ACCESS  not-accessible
    STATUS      current
    DESCRIPTION
            "A list of all slot14Type's utilization."
    ::= { slot14 1 }  

slot14Entry OBJECT-TYPE
    SYNTAX      Slot14Entry
    MAX-ACCESS  not-accessible
    STATUS      current
    DESCRIPTION
            "An entry contains a slot14's utilization."
    INDEX   { slot14Index }
    ::= { slot14Table 1 }

Slot14Entry ::=
    SEQUENCE {     
		slot14Index                       Integer32,
		slot14Type                        DisplayString,
		slot14Status                      DisplayString,
		slot14Id                          Integer32
    }  

slot14Index OBJECT-TYPE
    SYNTAX      Integer32 (1..2147483647)
    MAX-ACCESS  not-accessible
    STATUS      current
    DESCRIPTION
            "A unique value, greater than zero, for each chassis`s slot14."
    ::= { slot14Entry 1 }

slot14Type OBJECT-TYPE
    SYNTAX      DisplayString (SIZE (0..255))
    MAX-ACCESS  read-only
    STATUS      current
    DESCRIPTION
            "the slot14Type of each chassis."
    ::= { slot14Entry 2 }

slot14Status OBJECT-TYPE
    SYNTAX      DisplayString (SIZE (0..255))
    MAX-ACCESS  read-only
    STATUS      current
    DESCRIPTION
            "A string to describe the board status." 
    ::= { slot14Entry 3 }   

slot14Id OBJECT-TYPE
    SYNTAX      Integer32
    MAX-ACCESS  read-only
    STATUS      current
    DESCRIPTION
            "slot id."
    ::= { slot14Entry 4 }

slot14Module OBJECT IDENTIFIER ::= { slot14 2 }

-- slot14ModuleTable --
slot14ModuleTable OBJECT-TYPE
    SYNTAX      SEQUENCE OF Slot14ModuleEntry
    MAX-ACCESS  not-accessible
    STATUS      current
    DESCRIPTION
            "A list of all slot14Module's utilization."
    ::= { slot14Module 1 }  

slot14ModuleEntry OBJECT-TYPE
    SYNTAX      Slot14ModuleEntry
    MAX-ACCESS  not-accessible
    STATUS      current
    DESCRIPTION
            "An entry contains a slot14Module's utilization."
    INDEX   { slot14ModuleIndex }
    ::= { slot14ModuleTable 1 }

Slot14ModuleEntry ::=
    SEQUENCE {     
		slot14ModuleIndex                       Integer32,
		slot14ModuleId                           DisplayString,  
		slot14ModuleIfNumber                     Integer32		
    } 

slot14ModuleIndex OBJECT-TYPE
    SYNTAX      Integer32 (1..2147483647)
    MAX-ACCESS  not-accessible
    STATUS      current
    DESCRIPTION
            "A unique value, greater than zero, for each chassis`s slot14."
    ::= { slot14ModuleEntry 1 }

slot14ModuleId OBJECT-TYPE
    SYNTAX      DisplayString (SIZE (0..32))
    MAX-ACCESS  read-only
    STATUS      current
    DESCRIPTION
            "the value of module`s id"
    ::= { slot14ModuleEntry 2 }
  
slot14ModuleIfNumber OBJECT-TYPE
    SYNTAX      Integer32(0..2147483647)
    MAX-ACCESS  read-only
    STATUS      current
    DESCRIPTION
            "The number of network interfaces (regardless of their
            current state) present on this system." 
    ::= { slot14ModuleEntry 3 } 
    
slot14ModuleIfTable OBJECT-TYPE
    SYNTAX      SEQUENCE OF Slot14ModuleIfEntry
    MAX-ACCESS  not-accessible
    STATUS      current
    DESCRIPTION
            "A list of interface entries.  The number of entries is
            given by the value of ifNumber."
    ::= { slot14Module 2 } 
    
slot14ModuleIfEntry OBJECT-TYPE
    SYNTAX      Slot14ModuleIfEntry
    MAX-ACCESS  not-accessible
    STATUS      current
    DESCRIPTION
            "An entry containing management information applicable to a
            particular interface."
    INDEX   { slot14ModuleifIndex }
    ::= { slot14ModuleIfTable 1 }
    
Slot14ModuleIfEntry ::=
    SEQUENCE {
        slot14ModuleifIndex                 InterfaceIndex,  
        slot14ModuleIfId                    DisplayString,  
        slot14ModuleifDescr                 DisplayString,           
        slot14ModuleifType                  IANAifType,   		
        slot14ModuleifMtu                   Integer32,                
        slot14ModuleifSpeed                 Counter64,               
        slot14ModuleifPhysAddress           PhysAddress,              
        slot14ModuleifAdminStatus           INTEGER,                  
        slot14ModuleifOperStatus            INTEGER,                  
        slot14ModuleifLastChange            TimeTicks,                
	slot14ModuleifInKbits   	    Counter64,
	slot14ModuleifOutKbits              Counter64,
        slot14ModuleifInOctets              Counter64,                
        slot14ModuleifInUcastPkts           Counter64,                
        slot14ModuleifInNUcastPkts          Counter64,  
        slot14ModuleifInDiscards            Counter64,
        slot14ModuleifInErrors              Counter64,
        slot14ModuleifInFcsErrorPkts        Counter64,
        slot14ModuleifInUnknownProtos       Counter64,	-- deprecated
        slot14ModuleifOutOctets             Counter64,
        slot14ModuleifOutUcastPkts          Counter64,
        slot14ModuleifOutNUcastPkts         Counter64,  -- deprecated
        slot14ModuleifOutDiscards           Counter64,
        slot14ModuleifOutErrors             Counter64,
        slot14ModuleifOutFcsErrorPkts       Counter64,
        slot14ModuleifOutQLen               Gauge32,    -- deprecated  
	    slot14ModuleifInpps   	    Counter64,
	    slot14ModuleifOutpps              Counter64,        
        slot14ModuleifRxPower                DisplayString,
        slot14ModuleifTxPower                DisplayString,
        slot14ModuleifSpecific              OBJECT IDENTIFIER
    }         

slot14ModuleifIndex OBJECT-TYPE
    SYNTAX      InterfaceIndex
    MAX-ACCESS  read-only
    STATUS      current
    DESCRIPTION
            "A unique value, greater than zero, for each interface.  It
            is recommended that values are assigned contiguously
            starting from 1.  The value for each interface sub-layer
            must remain constant at least from one re-initialization of
            the entity's network management system to the next re-
            initialization."
    ::= { slot14ModuleIfEntry 1 }
    
slot14ModuleIfId OBJECT-TYPE
    SYNTAX      DisplayString (SIZE (0..32))
    MAX-ACCESS  read-only
    STATUS      current
    DESCRIPTION
            "the value of module`s id"
    ::= { slot14ModuleIfEntry 2 }
    
slot14ModuleifDescr OBJECT-TYPE
    SYNTAX      DisplayString (SIZE (0..255))
    MAX-ACCESS  read-only
    STATUS      current
    DESCRIPTION
            "A textual string containing information about the
            interface.  This string should include the name of the
            manufacturer, the product name and the version of the
            interface hardware/software."
    ::= { slot14ModuleIfEntry 3 }
    
slot14ModuleifType OBJECT-TYPE
    SYNTAX      IANAifType
    MAX-ACCESS  read-only
    STATUS      current
    DESCRIPTION
            "The type of interface.  Additional values for ifType are
            assigned by the Internet Assigned Numbers Authority (IANA),
            through updating the syntax of the IANAifType textual
            convention."
    ::= { slot14ModuleIfEntry 4 }

slot14ModuleifMtu OBJECT-TYPE
    SYNTAX      Integer32(1..2147483647)
    MAX-ACCESS  read-only
    STATUS      current
    DESCRIPTION
            "The size of the largest packet which can be sent/received
            on the interface, specified in octets.  For interfaces that
            are used for transmitting network datagrams, this is the
            size of the largest network datagram that can be sent on the
            interface."
    ::= { slot14ModuleIfEntry 5 }

slot14ModuleifSpeed OBJECT-TYPE
    SYNTAX      Counter64
    MAX-ACCESS  read-only
    STATUS      current
    DESCRIPTION
            "An estimate of the interface's current bandwidth in bits
            per second.  For interfaces which do not vary in bandwidth
            or for those where no accurate estimation can be made, this
            object should contain the nominal bandwidth. For a sub-layer
            which has no concept of bandwidth, this object should be zero."
    ::= { slot14ModuleIfEntry 6 }

slot14ModuleifPhysAddress OBJECT-TYPE
    SYNTAX      PhysAddress
    MAX-ACCESS  read-only
    STATUS      current
    DESCRIPTION
            "The interface's address at its protocol sub-layer.  For
            example, for an 802.x interface, this object normally
            contains a MAC address.  The interface's media-specific MIB
            must define the bit and byte ordering and the format of the
            value of this object.  For interfaces which do not have such
            an address (e.g., a serial line), this object should contain
            an octet string of zero length."
    ::= { slot14ModuleIfEntry 7 }
    
slot14ModuleifAdminStatus OBJECT-TYPE
    SYNTAX  INTEGER {
                up(1),       -- ready to pass packets
                down(2),
                testing(3)   -- in some test mode
            }
    MAX-ACCESS  read-write
    STATUS      current
    DESCRIPTION
            "The desired state of the interface.  The testing(3) state
            indicates that no operational packets can be passed.  When a
            managed system initializes, all interfaces start with
            ifAdminStatus in the down(2) state.  As a result of either
            explicit management action or per configuration information
            retained by the managed system, ifAdminStatus is then
            changed to either the up(1) or testing(3) states (or remains
            in the down(2) state)."
    ::= { slot14ModuleIfEntry 8 }

slot14ModuleifOperStatus OBJECT-TYPE
    SYNTAX  INTEGER {
                up(1),        -- ready to pass packets
                down(2),
                testing(3),   -- in some test mode
                unknown(4),   -- status can not be determined
                              -- for some reason.
                dormant(5),
                notPresent(6),    -- some component is missing
                lowerLayerDown(7) -- down due to state of
                                  -- lower-layer interface(s)
            }
    MAX-ACCESS  read-only
    STATUS      current
    DESCRIPTION
            "The current operational state of the interface.  The
            testing(3) state indicates that no operational packets can
            be passed.  If ifAdminStatus is down(2) then ifOperStatus
            should be down(2).  If ifAdminStatus is changed to up(1)
            then ifOperStatus should change to up(1) if the interface is
            ready to transmit and receive network traffic; it should
            change to dormant(5) if the interface is waiting for
            external actions (such as a serial line waiting for an
            incoming connection); it should remain in the down(2) state
            if and only if there is a fault that prevents it from going
            to the up(1) state; it should remain in the notPresent(6)
            state if the interface has missing (typically, hardware)
            components."
    ::= { slot14ModuleIfEntry 9 }

slot14ModuleifLastChange OBJECT-TYPE
    SYNTAX      TimeTicks
    MAX-ACCESS  read-only
    STATUS      current
    DESCRIPTION
            "The value of sysUpTime at the time the interface entered
            its current operational state.  If the current state was
            entered prior to the last re-initialization of the local
            network management subsystem, then this object contains a
            zero value."
    ::= { slot14ModuleIfEntry 10 }

slot14ModuleifInKbits OBJECT-TYPE
    SYNTAX      Counter64
    MAX-ACCESS  read-only
    STATUS      current
    DESCRIPTION
            "The real time rate received on the interface, in Kbits
	    format.

            Discontinuities in the value of this counter can occur at
            re-initialization of the management system, and at other
            times as indicated by the value of
            ifCounterDiscontinuityTime."
    ::= { slot14ModuleIfEntry 11 }

slot14ModuleifOutKbits OBJECT-TYPE
    SYNTAX      Counter64
    MAX-ACCESS  read-only
    STATUS      current
    DESCRIPTION
            "The real time rate send on the interface, in Kbits
	    format.

            Discontinuities in the value of this counter can occur at
            re-initialization of the management system, and at other
            times as indicated by the value of
            ifCounterDiscontinuityTime."
    ::= { slot14ModuleIfEntry 12 }

slot14ModuleifInOctets OBJECT-TYPE
    SYNTAX      Counter64
    MAX-ACCESS  read-only
    STATUS      current
    DESCRIPTION
            "The total number of octets received on the interface,
            including framing characters.

            Discontinuities in the value of this counter can occur at
            re-initialization of the management system, and at other
            times as indicated by the value of
            ifCounterDiscontinuityTime."
    ::= { slot14ModuleIfEntry 13 }

slot14ModuleifInUcastPkts OBJECT-TYPE
    SYNTAX      Counter64
    MAX-ACCESS  read-only
    STATUS      current
    DESCRIPTION
            "The number of packets, delivered by this sub-layer to a
            higher (sub-)layer, which were not addressed to a multicast
            or broadcast address at this sub-layer.

            Discontinuities in the value of this counter can occur at
            re-initialization of the management system, and at other
            times as indicated by the value of
            ifCounterDiscontinuityTime."
    ::= { slot14ModuleIfEntry 14 }

slot14ModuleifInNUcastPkts OBJECT-TYPE
    SYNTAX  Counter64
    MAX-ACCESS  read-only
    STATUS      current
    DESCRIPTION
            "The number of packets, delivered by this sub-layer to a
            higher (sub-)layer, which were addressed to a multicast or
            broadcast address at this sub-layer.

            Discontinuities in the value of this counter can occur at
            re-initialization of the management system, and at other
            times as indicated by the value of
            ifCounterDiscontinuityTime.

            This object is deprecated in favour of ifInMulticastPkts and
            ifInBroadcastPkts."
    ::= { slot14ModuleIfEntry 15 }

slot14ModuleifInDiscards OBJECT-TYPE
    SYNTAX      Counter64
    MAX-ACCESS  read-only
    STATUS      current
    DESCRIPTION
            "The number of inbound packets which were chosen to be
            discarded even though no errors had been detected to prevent

            their being deliverable to a higher-layer protocol.  One
            possible reason for discarding such a packet could be to
            free up buffer space.

            Discontinuities in the value of this counter can occur at
            re-initialization of the management system, and at other
            times as indicated by the value of
            ifCounterDiscontinuityTime."
    ::= { slot14ModuleIfEntry 16 }

slot14ModuleifInErrors OBJECT-TYPE
    SYNTAX      Counter64
    MAX-ACCESS  read-only
    STATUS      current
    DESCRIPTION
            "For packet-oriented interfaces, the number of inbound
            packets that contained errors preventing them from being
            deliverable to a higher-layer protocol.  For character-
            oriented or fixed-length interfaces, the number of inbound
            transmission units that contained errors preventing them
            from being deliverable to a higher-layer protocol.

            Discontinuities in the value of this counter can occur at
            re-initialization of the management system, and at other
            times as indicated by the value of
            ifCounterDiscontinuityTime."
    ::= { slot14ModuleIfEntry 17 }

slot14ModuleifInFcsErrorPkts OBJECT-TYPE
    SYNTAX      Counter64
    MAX-ACCESS  read-only
    STATUS      current
    DESCRIPTION
            "FCS error pakets."
    ::= { slot14ModuleIfEntry 18 }

slot14ModuleifInUnknownProtos OBJECT-TYPE
    SYNTAX      Counter64
    MAX-ACCESS  read-only
    STATUS      current
    DESCRIPTION
            "For packet-oriented interfaces, the number of packets
            received via the interface which were discarded because of
            an unknown or unsupported protocol.  For character-oriented
            or fixed-length interfaces that support protocol
            multiplexing the number of transmission units received via
            the interface which were discarded because of an unknown or
            unsupported protocol.  For any interface that does not
            support protocol multiplexing, this counter will always be
            0.

            Discontinuities in the value of this counter can occur at
            re-initialization of the management system, and at other
            times as indicated by the value of
            ifCounterDiscontinuityTime."
    ::= { slot14ModuleIfEntry 19 }

slot14ModuleifOutOctets OBJECT-TYPE
    SYNTAX      Counter64
    MAX-ACCESS  read-only
    STATUS      current
    DESCRIPTION
            "The total number of octets transmitted out of the
            interface, including framing characters.

            Discontinuities in the value of this counter can occur at
            re-initialization of the management system, and at other
            times as indicated by the value of
            ifCounterDiscontinuityTime."
    ::= { slot14ModuleIfEntry 20 }

slot14ModuleifOutUcastPkts OBJECT-TYPE
    SYNTAX      Counter64
    MAX-ACCESS  read-only
    STATUS      current
    DESCRIPTION
            "The total number of packets that higher-level protocols
            requested be transmitted, and which were not addressed to a
            multicast or broadcast address at this sub-layer, including
            those that were discarded or not sent.

            Discontinuities in the value of this counter can occur at
            re-initialization of the management system, and at other
            times as indicated by the value of
            ifCounterDiscontinuityTime."
    ::= { slot14ModuleIfEntry 21 }

slot14ModuleifOutNUcastPkts OBJECT-TYPE
    SYNTAX      Counter64
    MAX-ACCESS  read-only
    STATUS      deprecated
    DESCRIPTION
            "The total number of packets that higher-level protocols
            requested be transmitted, and which were addressed to a
            multicast or broadcast address at this sub-layer, including
            those that were discarded or not sent.

            Discontinuities in the value of this counter can occur at
            re-initialization of the management system, and at other
            times as indicated by the value of
            ifCounterDiscontinuityTime.

            This object is deprecated in favour of ifOutMulticastPkts
            and ifOutBroadcastPkts."
    ::= { slot14ModuleIfEntry 22 }

slot14ModuleifOutDiscards OBJECT-TYPE
    SYNTAX      Counter64
    MAX-ACCESS  read-only
    STATUS      current
    DESCRIPTION
            "The number of outbound packets which were chosen to be
            discarded even though no errors had been detected to prevent
            their being transmitted.  One possible reason for discarding
            such a packet could be to free up buffer space.

            Discontinuities in the value of this counter can occur at
            re-initialization of the management system, and at other
            times as indicated by the value of
            ifCounterDiscontinuityTime."
    ::= { slot14ModuleIfEntry 23 }

slot14ModuleifOutErrors OBJECT-TYPE
    SYNTAX      Counter64
    MAX-ACCESS  read-only
    STATUS      current
    DESCRIPTION
            "For packet-oriented interfaces, the number of outbound
            packets that could not be transmitted because of errors.
            For character-oriented or fixed-length interfaces, the
            number of outbound transmission units that could not be
            transmitted because of errors.

            Discontinuities in the value of this counter can occur at
            re-initialization of the management system, and at other
            times as indicated by the value of
            ifCounterDiscontinuityTime."
    ::= { slot14ModuleIfEntry 24 }

slot14ModuleifOutFcsErrorPkts OBJECT-TYPE
    SYNTAX      Counter64
    MAX-ACCESS  read-only
    STATUS      current
    DESCRIPTION
            "FCS error pakets."
    ::= { slot14ModuleIfEntry 25 }

slot14ModuleifOutQLen OBJECT-TYPE
    SYNTAX      Gauge32
    MAX-ACCESS  read-only
    STATUS      deprecated
    DESCRIPTION
            "The length of the output packet queue (in packets)."
    ::= { slot14ModuleIfEntry 26 }

slot14ModuleifInpps OBJECT-TYPE
    SYNTAX      Counter64
    MAX-ACCESS  read-only
    STATUS      current
    DESCRIPTION
            "The real time rate received on the interface, in pps
	    format.

            Discontinuities in the value of this counter can occur at
            re-initialization of the management system, and at other
            times as indicated by the value of
            ifCounterDiscontinuityTime."
    ::= { slot14ModuleIfEntry 27 }

slot14ModuleifOutpps OBJECT-TYPE
    SYNTAX      Counter64
    MAX-ACCESS  read-only
    STATUS      current
    DESCRIPTION
            "The real time rate send on the interface, in pps
	    format.

            Discontinuities in the value of this counter can occur at
            re-initialization of the management system, and at other
            times as indicated by the value of
            ifCounterDiscontinuityTime."
    ::= { slot14ModuleIfEntry 28 }

slot14ModuleifRxPower OBJECT-TYPE
    SYNTAX      DisplayString (SIZE (0..255))
    MAX-ACCESS  read-only
    STATUS      current
    DESCRIPTION
            "the value of interface's received power, in dbm format."
    ::= { slot14ModuleIfEntry 29 }
    
slot14ModuleifTxPower OBJECT-TYPE
    SYNTAX      DisplayString (SIZE (0..255))
    MAX-ACCESS  read-only
    STATUS      current
    DESCRIPTION
            "the value of interface's send power, in dbm format."
    ::= { slot14ModuleIfEntry 30 }

slot14ModuleifSpecific OBJECT-TYPE
    SYNTAX      OBJECT IDENTIFIER
    MAX-ACCESS  read-only
    STATUS      deprecated
    DESCRIPTION
            "A reference to MIB definitions specific to the particular
            media being used to realize the interface.  It is

            recommended that this value point to an instance of a MIB
            object in the media-specific MIB, i.e., that this object
            have the semantics associated with the InstancePointer
            textual convention defined in RFC 2579.  In fact, it is
            recommended that the media-specific MIB specify what value
            ifSpecific should/can take for values of ifType.  If no MIB
            definitions specific to the particular media are available,
            the value should be set to the OBJECT IDENTIFIER { 0 0 }."
    ::= { slot14ModuleIfEntry 31 }  

-- The boardPortManagement group --   
-- boardPortManagement --
boardInfoTable OBJECT-TYPE
     SYNTAX      SEQUENCE OF BoardInfoEntry
     MAX-ACCESS  not-accessible
     STATUS      current
     DESCRIPTION
             "A list of all boards's information."
     ::= { boardPortManagement 1 }   
    
boardInfoEntry OBJECT-TYPE
     SYNTAX      BoardInfoEntry
     MAX-ACCESS  not-accessible
     STATUS      current
     DESCRIPTION
             "An entry contains a board's information."
     INDEX   { statusChanged }
     ::= { boardInfoTable 1 } 

BoardInfoEntry ::= 
    SEQUENCE {    
                 statusChanged       DisplayString
     }   
    
statusChanged OBJECT-TYPE
     SYNTAX  DisplayString (SIZE (0..255))
     MAX-ACCESS  read-only
     STATUS      current
     DESCRIPTION
             "Board running status."
     ::= { boardInfoEntry 1 } 

-- traps --

linkProtectStatusChanged NOTIFICATION-TYPE
    STATUS  current
    DESCRIPTION
            "A link protect status changed trap signifies that the SNMP entity,
            acting in an agent role, has detected that the status
            is about to be changed."
    ::= { traps 1 }

cpuStatusChanged NOTIFICATION-TYPE
    STATUS  current
    DESCRIPTION
            "A cpu status change trap signifies that the SNMP entity,
            acting in an agent role, has detected that the cpu 
            status is about to be changed."
    ::= { traps 2 } 

memoryStatusChanged NOTIFICATION-TYPE
    STATUS  current
    DESCRIPTION
            "A memory status change trap signifies that the SNMP entity,
            acting in an agent role, has detected that the memory
            status is about to be changed."
    ::= { traps 3 } 

airFanStatusChanged NOTIFICATION-TYPE
    STATUS  current
    DESCRIPTION
            "A air fan status change trap signifies that the SNMP entity,
            acting in an agent role, has detected that the air fan
            status is about to be changed."
    ::= { traps 4 } 

powerStatusChanged NOTIFICATION-TYPE
    STATUS  current
    DESCRIPTION
            "A power status change trap signifies that the SNMP entity,
            acting in an agent role, has detected that the power 
            status is about to be changed."
    ::= { traps 5 } 


boardTemperatureStatusChanged NOTIFICATION-TYPE
    STATUS  current
    DESCRIPTION
            "A board status changed trap signifies that the SNMP entity,
            acting in an agent role, has detected that the board temperature
            status is about to be changed."
    ::= { traps 6 }

fcsStatusChanged NOTIFICATION-TYPE
    STATUS  current
    DESCRIPTION
            "A interface fcs status changed trap signifies that the SNMP entity,
            acting in an agent role, has detected that the interface's fcs
            status is about to be changed."
    ::= { traps 7 }

dropStatusChanged NOTIFICATION-TYPE
    STATUS  current
    DESCRIPTION
            "A interface drop status changed trap signifies that the SNMP entity,
            acting in an agent role, has detected that the interface's drop
            status is about to be changed."
    ::= { traps 8 }

boardStatusChanged NOTIFICATION-TYPE
    STATUS  current
    DESCRIPTION
            "A board running status changed trap signifies that the SNMP entity,
            acting in an agent role, has detected that the board's running
            status is about to be changed."
    ::= { traps 9 }

rxtxCounterStatusChanged NOTIFICATION-TYPE
    STATUS  current
    DESCRIPTION
            "A interface rx or tx counter status changed trap signifies that the SNMP entity,
            acting in an agent role, has detected that the board's running
            status is about to be changed."
    ::= { traps 10 }
rxByteStatusChanged NOTIFICATION-TYPE
    STATUS current
    DESCRIPTION
            "A interface rx bytes status changed trap signifies that the SNMP entity,
            acting in an agent role,has detected that the interface's rx bytes
            status is about to be changed."
    ::={ traps 11 }
overallRxStatusChanged NOTIFICATION-TYPE
   STATUS current
   DESCRIPTION
           "Overall rx bytes of all interface changed trap signifies that the SNMP entity,
           acting in an agent role,has detected that the overall rx bytes
           status is about to be changed."
   ::={ traps 12 }
txByteStatusChanged NOTIFICATION-TYPE
    STATUS current
    DESCRIPTION
            "A interface tx bytes status changed trap signifies that the SNMP entity,
            acting in an agent role,has detected that the interface's tx bytes
            status is about to be changed."
    ::={ traps 13 }
overallTxStatusChanged NOTIFICATION-TYPE
   STATUS current
   DESCRIPTION
           "Overall tx bytes of all interface changed trap signifies that the SNMP entity,
           acting in an agent role,has detected that the overall tx bytes
           status is about to be changed."
   ::={ traps 14 }

END
