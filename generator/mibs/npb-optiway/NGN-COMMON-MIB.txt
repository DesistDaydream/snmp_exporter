NGN-MIB DEFINITIONS ::= BEGIN

IMPORTS
    MODULE-IDENTITY, OBJECT-TYPE, Counter32,Gauge32, Counter64,
    Integer32,TimeTicks, NOTIFICATION-TYPE, enterprises             
        FROM SNMPv2-SMI
    TEXTUAL-CONVENTION, DisplayString,PhysAddress
       	FROM SNMPv2-TC
    IANAifType                              
    	FROM IANAifType-MIB;

ngnCommon MODULE-IDENTITY 
    LAST-UPDATED "201408250000Z"
    ORGANIZATION "Information technologies Co.,Ltd"
    CONTACT-INFO
             "EMail:      service@copyright.com"
    DESCRIPTION
            "The MIB module is for optiway_expII_1.4.0."
    REVISION      "201408250000Z"
    DESCRIPTION
            "Modify some compile syntax error."
    ::= { enterprises 53524 }


systemManagement OBJECT IDENTIFIER ::= { ngnCommon 1 } 
interfaces OBJECT IDENTIFIER ::= { ngnCommon 2 }
boardPortManagement OBJECT IDENTIFIER ::= { ngnCommon 3 }
traps OBJECT IDENTIFIER ::= { ngnCommon 4 }

InterfaceIndex ::= TEXTUAL-CONVENTION
    DISPLAY-HINT "d"
    STATUS       current
    DESCRIPTION
            "A unique value, greater than zero, for each interface or
            interface sub-layer in the managed system.  It is
            recommended that values are assigned contiguously starting
            from 1.  The value for each interface sub-layer must remain
            constant at least from one re-initialization of the entity's
            network management system to the next re-initialization."
    SYNTAX       Integer32 (1..2147483647)

-- The systemManagement group --

softwareVerion OBJECT-TYPE
    SYNTAX      DisplayString (SIZE (0..255))
    MAX-ACCESS  read-only
    STATUS      current
    DESCRIPTION
            "software verion."
    ::= { systemManagement 1 }
	
sysTime OBJECT-TYPE
    SYNTAX      DisplayString (SIZE (0..255))
    MAX-ACCESS  read-only
    STATUS      current
    DESCRIPTION
            "System Time."
    ::= { systemManagement 2 }
	
sysRunningTime OBJECT-TYPE
    SYNTAX      Integer32
    MAX-ACCESS  read-only
    STATUS      current
    DESCRIPTION
            "System running time. Unit is second."
    ::= { systemManagement 3 }
   
sysIp OBJECT-TYPE
    SYNTAX      DisplayString (SIZE (0..255))
    MAX-ACCESS  read-only
    STATUS      current
    DESCRIPTION
            "System Ip/Mask Addr."
    ::= { systemManagement 4 }

sysGateway OBJECT-TYPE
    SYNTAX      DisplayString (SIZE (0..255))
    MAX-ACCESS  read-only
    STATUS      current
    DESCRIPTION
            "System Gateway"
    ::= { systemManagement 5 }

-- cpuUtilizationTable --

cpuUtilizationTable OBJECT-TYPE
    SYNTAX      SEQUENCE OF CpuUtilizationEntry
    MAX-ACCESS  not-accessible
    STATUS      current
    DESCRIPTION
            "A list of all cpus's utilization."
    ::= { systemManagement 6 }  

cpuUtilizationEntry OBJECT-TYPE
    SYNTAX      CpuUtilizationEntry
    MAX-ACCESS  not-accessible
    STATUS      current
    DESCRIPTION
            "An entry contains a cpu's utilization."
    INDEX   { cpuIndex }
    ::= { cpuUtilizationTable 1 }

CpuUtilizationEntry ::=
    SEQUENCE {     
		cpuIndex                              Integer32,
		cpuUtilization                        Integer32,
        cpuClockSpeed                         DisplayString,
        cpuCoresNum                           Integer32,
        cputhreads                            Integer32,
        cpuus                                 DisplayString,
        cpusy                                 DisplayString,
        cpuwa                                 DisplayString,
        cpusi                                 DisplayString
    }  

cpuIndex OBJECT-TYPE
    SYNTAX      Integer32 (1..2147483647)
    MAX-ACCESS  read-only
    STATUS      current
    DESCRIPTION
            "A unique value, greater than zero, for each cpu."
    ::= { cpuUtilizationEntry 1 }

cpuUtilization OBJECT-TYPE
    SYNTAX      Integer32 (0..100)
    MAX-ACCESS  read-only
    STATUS      current
    DESCRIPTION
            "Cpu utilization in 5 ~ 30 second. Unit is %."
    ::= { cpuUtilizationEntry 2 }

cpuClockSpeed OBJECT-TYPE
    SYNTAX      DisplayString (SIZE (0..255))
    MAX-ACCESS  read-only
    STATUS      current
    DESCRIPTION
            "Cpu clock speed"
    ::= { cpuUtilizationEntry 3 }

cpuCoresNum OBJECT-TYPE
    SYNTAX      Integer32 (0..100)
    MAX-ACCESS  read-only
    STATUS      current
    DESCRIPTION
            "Cpu core nums"
    ::= { cpuUtilizationEntry 4 }

cputhreads OBJECT-TYPE
    SYNTAX      Integer32 (0..100)
    MAX-ACCESS  read-only
    STATUS      current
    DESCRIPTION
            "cpu threads nums"
    ::= { cpuUtilizationEntry 5 }

cpuus OBJECT-TYPE
    SYNTAX      DisplayString (SIZE (0..255))
    MAX-ACCESS  read-only
    STATUS      current
    DESCRIPTION
            "user CPU time"
    ::= { cpuUtilizationEntry 6 }

cpusy OBJECT-TYPE
    SYNTAX      DisplayString (SIZE (0..255))
    MAX-ACCESS  read-only
    STATUS      current
    DESCRIPTION
            "system CPU time"
    ::= { cpuUtilizationEntry 7 }

cpuwa OBJECT-TYPE
    SYNTAX      DisplayString (SIZE (0..255))
    MAX-ACCESS  read-only
    STATUS      current
    DESCRIPTION
            "iowait"
    ::= { cpuUtilizationEntry 8 }

cpusi OBJECT-TYPE
    SYNTAX      DisplayString (SIZE (0..255))
    MAX-ACCESS  read-only
    STATUS      current
    DESCRIPTION
            "software irq"
    ::= { cpuUtilizationEntry 9 }

-- memoryOccupancyRateTable --

memoryOccupancyRateTable OBJECT-TYPE
    SYNTAX      SEQUENCE OF MemoryOccupancyRateEntry
    MAX-ACCESS  not-accessible
    STATUS      current
    DESCRIPTION
            "A list of all memories's occupancy rate."
    ::= { systemManagement 7 }  

memoryOccupancyRateEntry OBJECT-TYPE
    SYNTAX      MemoryOccupancyRateEntry
    MAX-ACCESS  not-accessible
    STATUS      current
    DESCRIPTION
            "An entry contains a memory's occupancy rate."
    INDEX   { memoryIndex }
    ::= { memoryOccupancyRateTable 1 }

MemoryOccupancyRateEntry ::=
    SEQUENCE {     
		memoryIndex                     Integer32,
		maxmemory                       Counter32,
		memoryOccupancyRate             Integer32
    } 

memoryIndex OBJECT-TYPE
    SYNTAX      Integer32 (1..2147483647)
    MAX-ACCESS  not-accessible
    STATUS      current
    DESCRIPTION
            "A unique value, greater than zero, for each memory."
    ::= { memoryOccupancyRateEntry 1 }

maxmemory OBJECT-TYPE
    SYNTAX      Counter32
    MAX-ACCESS  read-only
    STATUS      current
    DESCRIPTION
            "Max memory. Unit is byte."
    ::= { memoryOccupancyRateEntry 2 }

memoryOccupancyRate OBJECT-TYPE
    SYNTAX      Integer32 (0..100)
    MAX-ACCESS  read-only
    STATUS      current
    DESCRIPTION
            "Memory occupancy rate. Unit is %."
    ::= { memoryOccupancyRateEntry 3 }


-- powerTable --

powerTable OBJECT-TYPE
    SYNTAX      SEQUENCE OF PowerEntry
    MAX-ACCESS  not-accessible
    STATUS      current
    DESCRIPTION
            "A list of all powers's status."
    ::= { systemManagement 8 }  

powerEntry OBJECT-TYPE
    SYNTAX      PowerEntry
    MAX-ACCESS  not-accessible
    STATUS      current
    DESCRIPTION
            "An entry contains a power's status."
    INDEX   { powerIndex }
    ::= { powerTable 1 }

PowerEntry ::=
    SEQUENCE {     
		powerIndex                     Integer32,
		powerId                        Integer32,
		powerStatus                    INTEGER
    } 

powerIndex OBJECT-TYPE
    SYNTAX      Integer32 (1..2147483647)
    MAX-ACCESS  not-accessible
    STATUS      current
    DESCRIPTION
            "A unique value, greater than zero, for each power."
    ::= { powerEntry 1 }

powerId OBJECT-TYPE
    SYNTAX      Integer32
    MAX-ACCESS  read-only
    STATUS      current
    DESCRIPTION
            "Power id."
    ::= { powerEntry 2 }

powerStatus OBJECT-TYPE
    SYNTAX  INTEGER {
                normal(1),
                abnormal(2),
                offline(3)
            }
    MAX-ACCESS  read-only
    STATUS      current
    DESCRIPTION
            "Power status."
    ::= { powerEntry 3 }

-- airFanTable --
airFanTable OBJECT-TYPE
    SYNTAX      SEQUENCE OF AirFanEntry
    MAX-ACCESS  not-accessible
    STATUS      current
    DESCRIPTION
            "A list of all air fans's status."
    ::= { systemManagement 9 }  
	
airFanEntry OBJECT-TYPE
    SYNTAX      AirFanEntry
    MAX-ACCESS  not-accessible
    STATUS      current
    DESCRIPTION
            "An entry contains an air fan's status."
    INDEX   { airFanIndex }
    ::= { airFanTable 1 }

AirFanEntry ::=
    SEQUENCE {     
		airFanIndex                     Integer32,
		airFanId                        Integer32,
		airFanStatus                    INTEGER
    } 
	
airFanIndex OBJECT-TYPE
    SYNTAX      Integer32 (1..2147483647)
    MAX-ACCESS  not-accessible
    STATUS      current
    DESCRIPTION
            "A unique value, greater than zero, for each air fan."
    ::= { airFanEntry 1 }

airFanId OBJECT-TYPE
    SYNTAX      Integer32
    MAX-ACCESS  read-only
    STATUS      current
    DESCRIPTION
            "Air fan id."
    ::= { airFanEntry 2 }

airFanStatus OBJECT-TYPE
    SYNTAX  INTEGER {
                normal(1),
                abnormal(2),
                offline(3)
            }
    MAX-ACCESS  read-only
    STATUS      current
    DESCRIPTION
            "Air fan status."
    ::= { airFanEntry 3 }
   
manuFacturers OBJECT-TYPE
    SYNTAX      DisplayString (SIZE (0..255))
    MAX-ACCESS  read-only
    STATUS      current
    DESCRIPTION
            "Board manufacturers"
    ::= { systemManagement 10 }

module OBJECT-TYPE
    SYNTAX      DisplayString (SIZE (0..255))
    MAX-ACCESS  read-only
    STATUS      current
    DESCRIPTION
            "Board manufacturers"
    ::= { systemManagement 11 }
   
deviceDescription OBJECT-TYPE
    SYNTAX      DisplayString (SIZE (0..255))
    MAX-ACCESS  read-only
    STATUS      current
    DESCRIPTION
            "Board manufacturers"
    ::= { systemManagement 12 }
   
hardwareVersion OBJECT-TYPE
    SYNTAX      DisplayString (SIZE (0..255))
    MAX-ACCESS  read-only
    STATUS      current
    DESCRIPTION
            "Board manufacturers"
    ::= { systemManagement 13 }
   
driveMode OBJECT-TYPE
    SYNTAX      DisplayString (SIZE (0..255))
    MAX-ACCESS  read-only
    STATUS      current
    DESCRIPTION
            "Drive mode"
    ::= { systemManagement 14 }
   
hardDriveCapacity OBJECT-TYPE
    SYNTAX      DisplayString (SIZE (0..255))
    MAX-ACCESS  read-only
    STATUS      current
    DESCRIPTION
            "Hard drice capacity"
    ::= { systemManagement 15 }
   
deviceAccessMode OBJECT-TYPE
    SYNTAX      DisplayString (SIZE (0..255))
    MAX-ACCESS  read-only
    STATUS      current
    DESCRIPTION
            "Device access mode"
    ::= { systemManagement 16 }


-- processTable --
processTable OBJECT-TYPE
    SYNTAX      SEQUENCE OF ProcessEntry
    MAX-ACCESS  not-accessible
    STATUS      current
    DESCRIPTION
            "A list of all process."
    ::= { systemManagement 17 }  
	
processEntry OBJECT-TYPE
    SYNTAX      ProcessEntry
    MAX-ACCESS  not-accessible
    STATUS      current
    DESCRIPTION
            "An entry contains an process information."
    INDEX   { processIndex }
    ::= { processTable 1 }

ProcessEntry ::=
    SEQUENCE {     
		processIndex                     Integer32,
		processName                      DisplayString,
        processCpuOccupancyRate          Integer32,
        processMemOccupancyRate          Integer32
    } 
	
processIndex OBJECT-TYPE
    SYNTAX      Integer32 (1..2147483647)
    MAX-ACCESS  not-accessible
    STATUS      current
    DESCRIPTION
            "A unique value, greater than zero, for each process."
    ::= { processEntry 1 }

processName OBJECT-TYPE
    SYNTAX      DisplayString
    MAX-ACCESS  read-only
    STATUS      current
    DESCRIPTION
            "Process name."
    ::= { processEntry 2 }

processCpuOccupancyRate OBJECT-TYPE
    SYNTAX      Integer32 (1..2147483647) 
    MAX-ACCESS  read-only
    STATUS      current
    DESCRIPTION
            "Process cpu occupancy rate."
    ::= { processEntry 3 }

processMemOccupancyRate OBJECT-TYPE
    SYNTAX      Integer32 (1..2147483647) 
    MAX-ACCESS  read-only
    STATUS      current
    DESCRIPTION
            "Process memory occupancy rate."
    ::= { processEntry 4 }

cpuTotalUseRate OBJECT-TYPE
    SYNTAX      DisplayString (SIZE (0..255))
    MAX-ACCESS  read-only
    STATUS      current
    DESCRIPTION
            "CPU total utilization"
    ::= { systemManagement 18 }

slotConfig OBJECT-TYPE
    SYNTAX      DisplayString (SIZE (0..255))
    MAX-ACCESS  read-only
    STATUS      current
    DESCRIPTION
            "Slot configuration"
    ::= { systemManagement 19 }
    
-- The Interfaces group

-- InterfaceIndex contains the semantics of ifIndex and should be used
-- for any objects defined in other MIB modules that need these semantics.      

slotNumber  OBJECT-TYPE
    SYNTAX      Integer32
    MAX-ACCESS  read-only
    STATUS      current
    DESCRIPTION
            "The number of board present on this system."
    ::= { interfaces 1 }

slot1  OBJECT IDENTIFIER ::= { interfaces 2 } 
slot2  OBJECT IDENTIFIER ::= { interfaces 3 }
slot3  OBJECT IDENTIFIER ::= { interfaces 4 }
slot4  OBJECT IDENTIFIER ::= { interfaces 5 }
slot5  OBJECT IDENTIFIER ::= { interfaces 6 }
slot6  OBJECT IDENTIFIER ::= { interfaces 7 }
slot7  OBJECT IDENTIFIER ::= { interfaces 8 }
slot8  OBJECT IDENTIFIER ::= { interfaces 9 }
slot9  OBJECT IDENTIFIER ::= { interfaces 10 }
slot10 OBJECT IDENTIFIER ::= { interfaces 11 }
slot11 OBJECT IDENTIFIER ::= { interfaces 12 }
slot12 OBJECT IDENTIFIER ::= { interfaces 13 }
slot13 OBJECT IDENTIFIER ::= { interfaces 14 }
slot14 OBJECT IDENTIFIER ::= { interfaces 15 }
slot15 OBJECT IDENTIFIER ::= { interfaces 16 }
slot16 OBJECT IDENTIFIER ::= { interfaces 17 }
		
-- slot 1 --

-- slot1Table --

slot1Table OBJECT-TYPE
    SYNTAX      SEQUENCE OF Slot1Entry
    MAX-ACCESS  not-accessible
    STATUS      current
    DESCRIPTION
            "A list of all slot1Type's utilization."
    ::= { slot1 1 }  

slot1Entry OBJECT-TYPE
    SYNTAX      Slot1Entry
    MAX-ACCESS  not-accessible
    STATUS      current
    DESCRIPTION
            "An entry contains a slot1's utilization."
    INDEX   { slot1Index }
    ::= { slot1Table 1 }

Slot1Entry ::=
    SEQUENCE {     
		slot1Index                       Integer32,
		slot1Type                        DisplayString,
		slot1Status                      DisplayString,
        slot1SerialNumber                DisplayString,		
        slot1Temperature                 DisplayString
    }  

slot1Index OBJECT-TYPE
    SYNTAX      Integer32 (1..2147483647)
    MAX-ACCESS  not-accessible
    STATUS      current
    DESCRIPTION
            "A unique value, greater than zero, for each chassis`s slot1."
    ::= { slot1Entry 1 }

slot1Type OBJECT-TYPE
    SYNTAX      DisplayString (SIZE (0..255))
    MAX-ACCESS  read-only
    STATUS      current
    DESCRIPTION
            "the slot1Type of each chassis."
    ::= { slot1Entry 2 }

slot1Status OBJECT-TYPE
    SYNTAX      DisplayString (SIZE (0..255))
    MAX-ACCESS  read-only
    STATUS      current
    DESCRIPTION
            "A string to describe the board status." 
    ::= { slot1Entry 3 }   

slot1SerialNumber OBJECT-TYPE
    SYNTAX      DisplayString (SIZE (0..255))
    MAX-ACCESS  read-only
    STATUS      current
    DESCRIPTION
            "A string to describe the board serial number." 
    ::= { slot1Entry 4 }   

slot1Temperature OBJECT-TYPE
    SYNTAX      DisplayString (SIZE (0..255))
    MAX-ACCESS  read-only
    STATUS      current
    DESCRIPTION
            "A string to describe the board temperature." 
    ::= { slot1Entry 5 }   

slot1Module OBJECT IDENTIFIER ::= { slot1 2 }

-- slot1ModuleTable --
slot1ModuleTable OBJECT-TYPE
    SYNTAX      SEQUENCE OF Slot1ModuleEntry
    MAX-ACCESS  not-accessible
    STATUS      current
    DESCRIPTION
            "A list of all slot1Module's utilization."
    ::= { slot1Module 1 }  

slot1ModuleEntry OBJECT-TYPE
    SYNTAX      Slot1ModuleEntry
    MAX-ACCESS  not-accessible
    STATUS      current
    DESCRIPTION
            "An entry contains a slot1Module's utilization."
    INDEX   { slot1ModuleIndex }
    ::= { slot1ModuleTable 1 }

Slot1ModuleEntry ::=
    SEQUENCE {     
		slot1ModuleIndex                       Integer32,
		slot1ModuleId                           DisplayString,  
		slot1ModuleIfNumber                     Integer32		
    } 

slot1ModuleIndex OBJECT-TYPE
    SYNTAX      Integer32 (1..2147483647)
    MAX-ACCESS  not-accessible
    STATUS      current
    DESCRIPTION
            "A unique value, greater than zero, for each chassis`s slot1."
    ::= { slot1ModuleEntry 1 }

slot1ModuleId OBJECT-TYPE
    SYNTAX      DisplayString (SIZE (0..32))
    MAX-ACCESS  read-only
    STATUS      current
    DESCRIPTION
            "the value of module`s id"
    ::= { slot1ModuleEntry 2 }
  
slot1ModuleIfNumber OBJECT-TYPE
    SYNTAX      Integer32(0..2147483647)
    MAX-ACCESS  read-only
    STATUS      current
    DESCRIPTION
            "The number of network interfaces (regardless of their
            current state) present on this system." 
    ::= { slot1ModuleEntry 3 } 
    
slot1ModuleIfTable OBJECT-TYPE
    SYNTAX      SEQUENCE OF Slot1ModuleIfEntry
    MAX-ACCESS  not-accessible
    STATUS      current
    DESCRIPTION
            "A list of interface entries.  The number of entries is
            given by the value of ifNumber."
    ::= { slot1Module 2 } 
    
slot1ModuleIfEntry OBJECT-TYPE
    SYNTAX      Slot1ModuleIfEntry
    MAX-ACCESS  not-accessible
    STATUS      current
    DESCRIPTION
            "An entry containing management information applicable to a
            particular interface."
    INDEX   { slot1ModuleifIndex }
    ::= { slot1ModuleIfTable 1 }
    
Slot1ModuleIfEntry ::=
    SEQUENCE {
        slot1ModuleifIndex                 InterfaceIndex,  
        slot1ModuleIfId                    DisplayString,  
        slot1ModuleifDescr                 DisplayString,           
        slot1ModuleifType                  IANAifType,   		
        slot1ModuleifMtu                   Integer32,                
        slot1ModuleifSpeed                 Counter64,               
        slot1ModuleifPhysAddress           PhysAddress,              
        slot1ModuleifAdminStatus           INTEGER,                  
        slot1ModuleifOperStatus            INTEGER,                  
        slot1ModuleifLastChange            TimeTicks,                
        slot1ModuleifInOctets              Counter64,                
        slot1ModuleifInUcastPkts           Counter64,                
        slot1ModuleifInNUcastPkts          Counter64,  
        slot1ModuleifInDiscards            Counter64,
        slot1ModuleifInErrors              Counter64,
        slot1ModuleifInFcsErrorPkts        Counter64,
        slot1ModuleifInUnknownProtos       Counter64,	-- deprecated
        slot1ModuleifOutOctets             Counter64,
        slot1ModuleifOutUcastPkts          Counter64,
        slot1ModuleifOutNUcastPkts         Counter64,  -- deprecated
        slot1ModuleifOutDiscards           Counter64,
        slot1ModuleifOutErrors             Counter64,
        slot1ModuleifOutFcsErrorPkts       Counter64,
        slot1ModuleifOutQLen               Gauge32,    -- deprecated  
        slot1ModuleifOutOctetsRate         Counter64,
        slot1ModuleifInOctetsRate          Counter64,
        slot1ModuleifOutPktsRate           Counter64,
        slot1ModuleifInPktsRate            Counter64,
        slot1ModuleifRxPower               DisplayString,
        slot1ModuleifTxPower               DisplayString,
        slot1ModuleifSpecific              OBJECT IDENTIFIER,
        slot1ModuleifTxMirrorList          DisplayString,
        slot1ModuleifRxMirrorList          DisplayString,
        slot1ModuleifRxPowerMin               DisplayString,
        slot1ModuleifRxPowerMax               DisplayString,
        slot1ModuleifTxPowerMin               DisplayString,
        slot1ModuleifTxPowerMax               DisplayString,
        slot1ModuleifRxHisPeak            Counter64,
        slot1ModuleifTxHisPeak            Counter64,
        slot1ModuleifMode                 DisplayString    		
    }         

slot1ModuleifIndex OBJECT-TYPE
    SYNTAX      InterfaceIndex
    MAX-ACCESS  read-only
    STATUS      current
    DESCRIPTION
            "A unique value, greater than zero, for each interface.  It
            is recommended that values are assigned contiguously
            starting from 1.  The value for each interface sub-layer
            must remain constant at least from one re-initialization of
            the entity's network management system to the next re-
            initialization."
    ::= { slot1ModuleIfEntry 1 }
    
slot1ModuleIfId OBJECT-TYPE
    SYNTAX      DisplayString (SIZE (0..32))
    MAX-ACCESS  read-only
    STATUS      current
    DESCRIPTION
            "the value of module`s id"
    ::= { slot1ModuleIfEntry 2 }
    
slot1ModuleifDescr OBJECT-TYPE
    SYNTAX      DisplayString (SIZE (0..255))
    MAX-ACCESS  read-only
    STATUS      current
    DESCRIPTION
            "A textual string containing information about the
            interface.  This string should include the name of the
            manufacturer, the product name and the version of the
            interface hardware/software."
    ::= { slot1ModuleIfEntry 3 }
    
slot1ModuleifType OBJECT-TYPE
    SYNTAX      IANAifType
    MAX-ACCESS  read-only
    STATUS      current
    DESCRIPTION
            "The type of interface.  Additional values for ifType are
            assigned by the Internet Assigned Numbers Authority (IANA),
            through updating the syntax of the IANAifType textual
            convention."
    ::= { slot1ModuleIfEntry 4 }

slot1ModuleifMtu OBJECT-TYPE
    SYNTAX      Integer32(1..2147483647)
    MAX-ACCESS  read-only
    STATUS      current
    DESCRIPTION
            "The size of the largest packet which can be sent/received
            on the interface, specified in octets.  For interfaces that
            are used for transmitting network datagrams, this is the
            size of the largest network datagram that can be sent on the
            interface."
    ::= { slot1ModuleIfEntry 5 }

slot1ModuleifSpeed OBJECT-TYPE
    SYNTAX      Counter64
    MAX-ACCESS  read-only
    STATUS      current
    DESCRIPTION
            "An estimate of the interface's current bandwidth in bits
            per second.  For interfaces which do not vary in bandwidth
            or for those where no accurate estimation can be made, this
            object should contain the nominal bandwidth. For a sub-layer
            which has no concept of bandwidth, this object should be zero."
    ::= { slot1ModuleIfEntry 6 }

slot1ModuleifPhysAddress OBJECT-TYPE
    SYNTAX      PhysAddress
    MAX-ACCESS  read-only
    STATUS      current
    DESCRIPTION
            "The interface's address at its protocol sub-layer.  For
            example, for an 802.x interface, this object normally
            contains a MAC address.  The interface's media-specific MIB
            must define the bit and byte ordering and the format of the
            value of this object.  For interfaces which do not have such
            an address (e.g., a serial line), this object should contain
            an octet string of zero length."
    ::= { slot1ModuleIfEntry 7 }
    
slot1ModuleifAdminStatus OBJECT-TYPE
    SYNTAX  INTEGER {
                up(1),       -- ready to pass packets
                down(2),
                testing(3)   -- in some test mode
            }
    MAX-ACCESS  read-write
    STATUS      current
    DESCRIPTION
            "The desired state of the interface.  The testing(3) state
            indicates that no operational packets can be passed.  When a
            managed system initializes, all interfaces start with
            ifAdminStatus in the down(2) state.  As a result of either
            explicit management action or per configuration information
            retained by the managed system, ifAdminStatus is then
            changed to either the up(1) or testing(3) states (or remains
            in the down(2) state)."
    ::= { slot1ModuleIfEntry 8 }

slot1ModuleifOperStatus OBJECT-TYPE
    SYNTAX  INTEGER {
                up(1),        -- ready to pass packets
                down(2),
                testing(3),   -- in some test mode
                unknown(4),   -- status can not be determined
                              -- for some reason.
                dormant(5),
                notPresent(6),    -- some component is missing
                lowerLayerDown(7) -- down due to state of
                                  -- lower-layer interface(s)
            }
    MAX-ACCESS  read-only
    STATUS      current
    DESCRIPTION
            "The current operational state of the interface.  The
            testing(3) state indicates that no operational packets can
            be passed.  If ifAdminStatus is down(2) then ifOperStatus
            should be down(2).  If ifAdminStatus is changed to up(1)
            then ifOperStatus should change to up(1) if the interface is
            ready to transmit and receive network traffic; it should
            change to dormant(5) if the interface is waiting for
            external actions (such as a serial line waiting for an
            incoming connection); it should remain in the down(2) state
            if and only if there is a fault that prevents it from going
            to the up(1) state; it should remain in the notPresent(6)
            state if the interface has missing (typically, hardware)
            components."
    ::= { slot1ModuleIfEntry 9 }

slot1ModuleifLastChange OBJECT-TYPE
    SYNTAX      TimeTicks
    MAX-ACCESS  read-only
    STATUS      current
    DESCRIPTION
            "The value of sysUpTime at the time the interface entered
            its current operational state.  If the current state was
            entered prior to the last re-initialization of the local
            network management subsystem, then this object contains a
            zero value."
    ::= { slot1ModuleIfEntry 10 }

slot1ModuleifInOctets OBJECT-TYPE
    SYNTAX      Counter64
    MAX-ACCESS  read-only
    STATUS      current
    DESCRIPTION
            "The total number of octets received on the interface,
            including framing characters.

            Discontinuities in the value of this counter can occur at
            re-initialization of the management system, and at other
            times as indicated by the value of
            ifCounterDiscontinuityTime."
    ::= { slot1ModuleIfEntry 11 }

slot1ModuleifInUcastPkts OBJECT-TYPE
    SYNTAX      Counter64
    MAX-ACCESS  read-only
    STATUS      current
    DESCRIPTION
            "The number of packets, delivered by this sub-layer to a
            higher (sub-)layer, which were not addressed to a multicast
            or broadcast address at this sub-layer.

            Discontinuities in the value of this counter can occur at
            re-initialization of the management system, and at other
            times as indicated by the value of
            ifCounterDiscontinuityTime."
    ::= { slot1ModuleIfEntry 12 }

slot1ModuleifInNUcastPkts OBJECT-TYPE
    SYNTAX  Counter64
    MAX-ACCESS  read-only
    STATUS      current
    DESCRIPTION
            "The number of packets, delivered by this sub-layer to a
            higher (sub-)layer, which were addressed to a multicast or
            broadcast address at this sub-layer.

            Discontinuities in the value of this counter can occur at
            re-initialization of the management system, and at other
            times as indicated by the value of
            ifCounterDiscontinuityTime.

            This object is deprecated in favour of ifInMulticastPkts and
            ifInBroadcastPkts."
    ::= { slot1ModuleIfEntry 13 }

slot1ModuleifInDiscards OBJECT-TYPE
    SYNTAX      Counter64
    MAX-ACCESS  read-only
    STATUS      current
    DESCRIPTION
            "The number of inbound packets which were chosen to be
            discarded even though no errors had been detected to prevent

            their being deliverable to a higher-layer protocol.  One
            possible reason for discarding such a packet could be to
            free up buffer space.

            Discontinuities in the value of this counter can occur at
            re-initialization of the management system, and at other
            times as indicated by the value of
            ifCounterDiscontinuityTime."
    ::= { slot1ModuleIfEntry 14 }

slot1ModuleifInErrors OBJECT-TYPE
    SYNTAX      Counter64
    MAX-ACCESS  read-only
    STATUS      current
    DESCRIPTION
            "For packet-oriented interfaces, the number of inbound
            packets that contained errors preventing them from being
            deliverable to a higher-layer protocol.  For character-
            oriented or fixed-length interfaces, the number of inbound
            transmission units that contained errors preventing them
            from being deliverable to a higher-layer protocol.

            Discontinuities in the value of this counter can occur at
            re-initialization of the management system, and at other
            times as indicated by the value of
            ifCounterDiscontinuityTime."
    ::= { slot1ModuleIfEntry 15 }

slot1ModuleifInFcsErrorPkts OBJECT-TYPE
    SYNTAX      Counter64
    MAX-ACCESS  read-only
    STATUS      current
    DESCRIPTION
            "FCS error pakets."
    ::= { slot1ModuleIfEntry 16 }

slot1ModuleifInUnknownProtos OBJECT-TYPE
    SYNTAX      Counter64
    MAX-ACCESS  read-only
    STATUS      current
    DESCRIPTION
            "For packet-oriented interfaces, the number of packets
            received via the interface which were discarded because of
            an unknown or unsupported protocol.  For character-oriented
            or fixed-length interfaces that support protocol
            multiplexing the number of transmission units received via
            the interface which were discarded because of an unknown or
            unsupported protocol.  For any interface that does not
            support protocol multiplexing, this counter will always be
            0.

            Discontinuities in the value of this counter can occur at
            re-initialization of the management system, and at other
            times as indicated by the value of
            ifCounterDiscontinuityTime."
    ::= { slot1ModuleIfEntry 17 }

slot1ModuleifOutOctets OBJECT-TYPE
    SYNTAX      Counter64
    MAX-ACCESS  read-only
    STATUS      current
    DESCRIPTION
            "The total number of octets transmitted out of the
            interface, including framing characters.

            Discontinuities in the value of this counter can occur at
            re-initialization of the management system, and at other
            times as indicated by the value of
            ifCounterDiscontinuityTime."
    ::= { slot1ModuleIfEntry 18 }

slot1ModuleifOutUcastPkts OBJECT-TYPE
    SYNTAX      Counter64
    MAX-ACCESS  read-only
    STATUS      current
    DESCRIPTION
            "The total number of packets that higher-level protocols
            requested be transmitted, and which were not addressed to a
            multicast or broadcast address at this sub-layer, including
            those that were discarded or not sent.

            Discontinuities in the value of this counter can occur at
            re-initialization of the management system, and at other
            times as indicated by the value of
            ifCounterDiscontinuityTime."
    ::= { slot1ModuleIfEntry 19 }

slot1ModuleifOutNUcastPkts OBJECT-TYPE
    SYNTAX      Counter64
    MAX-ACCESS  read-only
    STATUS      deprecated
    DESCRIPTION
            "The total number of packets that higher-level protocols
            requested be transmitted, and which were addressed to a
            multicast or broadcast address at this sub-layer, including
            those that were discarded or not sent.

            Discontinuities in the value of this counter can occur at
            re-initialization of the management system, and at other
            times as indicated by the value of
            ifCounterDiscontinuityTime.

            This object is deprecated in favour of ifOutMulticastPkts
            and ifOutBroadcastPkts."
    ::= { slot1ModuleIfEntry 20 }

slot1ModuleifOutDiscards OBJECT-TYPE
    SYNTAX      Counter64
    MAX-ACCESS  read-only
    STATUS      current
    DESCRIPTION
            "The number of outbound packets which were chosen to be
            discarded even though no errors had been detected to prevent
            their being transmitted.  One possible reason for discarding
            such a packet could be to free up buffer space.

            Discontinuities in the value of this counter can occur at
            re-initialization of the management system, and at other
            times as indicated by the value of
            ifCounterDiscontinuityTime."
    ::= { slot1ModuleIfEntry 21 }

slot1ModuleifOutErrors OBJECT-TYPE
    SYNTAX      Counter64
    MAX-ACCESS  read-only
    STATUS      current
    DESCRIPTION
            "For packet-oriented interfaces, the number of outbound
            packets that could not be transmitted because of errors.
            For character-oriented or fixed-length interfaces, the
            number of outbound transmission units that could not be
            transmitted because of errors.

            Discontinuities in the value of this counter can occur at
            re-initialization of the management system, and at other
            times as indicated by the value of
            ifCounterDiscontinuityTime."
    ::= { slot1ModuleIfEntry 22 }

slot1ModuleifOutFcsErrorPkts OBJECT-TYPE
    SYNTAX      Counter64
    MAX-ACCESS  read-only
    STATUS      current
    DESCRIPTION
            "FCS error pakets."
    ::= { slot1ModuleIfEntry 23 }

slot1ModuleifOutQLen OBJECT-TYPE
    SYNTAX      Gauge32
    MAX-ACCESS  read-only
    STATUS      deprecated
    DESCRIPTION
            "The length of the output packet queue (in packets)."
    ::= { slot1ModuleIfEntry 24 }

slot1ModuleifOutOctetsRate OBJECT-TYPE
    SYNTAX      Counter64
    MAX-ACCESS  read-only
    STATUS      current
    DESCRIPTION
            "The speed of octets trans on the interface(kbps)"
    ::= { slot1ModuleIfEntry 25 }

slot1ModuleifInOctetsRate OBJECT-TYPE
    SYNTAX      Counter64
    MAX-ACCESS  read-only
    STATUS      current
    DESCRIPTION
            "The speed of octets received on the interface(kbps)"
    ::= { slot1ModuleIfEntry 26 }

slot1ModuleifOutPktsRate OBJECT-TYPE
    SYNTAX      Counter64
    MAX-ACCESS  read-only
    STATUS      current
    DESCRIPTION
            "The speed of packets trans on the interface(pps)"
    ::= { slot1ModuleIfEntry 27 }

slot1ModuleifInPktsRate OBJECT-TYPE
    SYNTAX      Counter64
    MAX-ACCESS  read-only
    STATUS      current
    DESCRIPTION
            "The speed of octets received on the interface(kbps)"
    ::= { slot1ModuleIfEntry 28 }

slot1ModuleifRxPower OBJECT-TYPE
    SYNTAX      DisplayString (SIZE (0..255))
    MAX-ACCESS  read-only
    STATUS      current
    DESCRIPTION
            "the value of interface's received power, in dbm format."
    ::= { slot1ModuleIfEntry 29 }

slot1ModuleifTxPower OBJECT-TYPE
    SYNTAX      DisplayString (SIZE (0..255))
    MAX-ACCESS  read-only
    STATUS      current
    DESCRIPTION
            "the value of interface's send power, in dbm format."
    ::= { slot1ModuleIfEntry 30 }

slot1ModuleifSpecific OBJECT-TYPE
    SYNTAX      OBJECT IDENTIFIER
    MAX-ACCESS  read-only
    STATUS      deprecated
    DESCRIPTION
            "A reference to MIB definitions specific to the particular
            media being used to realize the interface.  It is

            recommended that this value point to an instance of a MIB
            object in the media-specific MIB, i.e., that this object
            have the semantics associated with the InstancePointer
            textual convention defined in RFC 2579.  In fact, it is
            recommended that the media-specific MIB specify what value
            ifSpecific should/can take for values of ifType.  If no MIB
            definitions specific to the particular media are available,
            the value should be set to the OBJECT IDENTIFIER { 0 0 }."
    ::= { slot1ModuleIfEntry 31 }  
 
slot1ModuleifTxMirrorList OBJECT-TYPE
    SYNTAX      DisplayString (SIZE (0..255))
    MAX-ACCESS  read-only
    STATUS      deprecated
    DESCRIPTION
            "the interface tx mirror list."
    ::= { slot1ModuleIfEntry 32 }  
 
slot1ModuleifRxMirrorList OBJECT-TYPE
    SYNTAX      DisplayString (SIZE (0..255))
    MAX-ACCESS  read-only
    STATUS      deprecated
    DESCRIPTION
            "the interface rx mirror list."
    ::= { slot1ModuleIfEntry 33 }  

slot1ModuleifRxPowerMin OBJECT-TYPE
    SYNTAX      DisplayString (SIZE (0..255))
    MAX-ACCESS  read-only
    STATUS      deprecated
    DESCRIPTION
            "the interface min rx power."
    ::= { slot1ModuleIfEntry 34 }  

slot1ModuleifRxPowerMax OBJECT-TYPE
    SYNTAX      DisplayString (SIZE (0..255))
    MAX-ACCESS  read-only
    STATUS      deprecated
    DESCRIPTION
            "the interface max rx power."
    ::= { slot1ModuleIfEntry 35 }  

slot1ModuleifTxPowerMin OBJECT-TYPE
    SYNTAX      DisplayString (SIZE (0..255))
    MAX-ACCESS  read-only
    STATUS      deprecated
    DESCRIPTION
            "the interface min tx power."
    ::= { slot1ModuleIfEntry 36 }  

slot1ModuleifTxPowerMax OBJECT-TYPE
    SYNTAX      DisplayString (SIZE (0..255))
    MAX-ACCESS  read-only
    STATUS      deprecated
    DESCRIPTION
            "the interface max tx power."
    ::= { slot1ModuleIfEntry 37 }  

slot1ModuleifRxHisPeak OBJECT-TYPE
    SYNTAX      Counter64
    MAX-ACCESS  read-only
    STATUS      current
    DESCRIPTION
            "The max speed of rx rate on the interface(kbps)"
    ::= { slot1ModuleIfEntry 38 }

slot1ModuleifTxHisPeak OBJECT-TYPE
    SYNTAX      Counter64
    MAX-ACCESS  read-only
    STATUS      current
    DESCRIPTION
            "The max speed of tx rate on the interface(kbps)"
    ::= { slot1ModuleIfEntry 39 }

slot1ModuleifMode OBJECT-TYPE
    SYNTAX      DisplayString (SIZE (0..255))
    MAX-ACCESS  read-only
    STATUS      deprecated
    DESCRIPTION
            "the interface if mode."
    ::= { slot1ModuleIfEntry 40 }  

-- slot 2 --

-- slot2Table --

slot2Table OBJECT-TYPE
    SYNTAX      SEQUENCE OF Slot2Entry
    MAX-ACCESS  not-accessible
    STATUS      current
    DESCRIPTION
            "A list of all slot2Type's utilization."
    ::= { slot2 1 }  

slot2Entry OBJECT-TYPE
    SYNTAX      Slot2Entry
    MAX-ACCESS  not-accessible
    STATUS      current
    DESCRIPTION
            "An entry contains a slot2's utilization."
    INDEX   { slot2Index }
    ::= { slot2Table 1 }

Slot2Entry ::=
    SEQUENCE {     
		slot2Index                       Integer32,
		slot2Type                        DisplayString,
		slot2Status                      DisplayString,		
        slot2SerialNumber                DisplayString,		
        slot2Temperature                 DisplayString
    }  

slot2Index OBJECT-TYPE
    SYNTAX      Integer32 (1..2147483647)
    MAX-ACCESS  not-accessible
    STATUS      current
    DESCRIPTION
            "A unique value, greater than zero, for each chassis`s slot2."
    ::= { slot2Entry 1 }

slot2Type OBJECT-TYPE
    SYNTAX      DisplayString (SIZE (0..255))
    MAX-ACCESS  read-only
    STATUS      current
    DESCRIPTION
            "the slot2Type of each chassis."
    ::= { slot2Entry 2 }

slot2Status OBJECT-TYPE
    SYNTAX      DisplayString (SIZE (0..255))
    MAX-ACCESS  read-only
    STATUS      current
    DESCRIPTION
            "A string to describe the board status." 
    ::= { slot2Entry 3 }   

slot2SerialNumber OBJECT-TYPE
    SYNTAX      DisplayString (SIZE (0..255))
    MAX-ACCESS  read-only
    STATUS      current
    DESCRIPTION
            "A string to describe the board serial number." 
    ::= { slot2Entry 4 }   

slot2Temperature OBJECT-TYPE
    SYNTAX      DisplayString (SIZE (0..255))
    MAX-ACCESS  read-only
    STATUS      current
    DESCRIPTION
            "A string to describe the board temperature." 
    ::= { slot2Entry 5 }   


slot2Module OBJECT IDENTIFIER ::= { slot2 2 }

-- slot2ModuleTable --
slot2ModuleTable OBJECT-TYPE
    SYNTAX      SEQUENCE OF Slot2ModuleEntry
    MAX-ACCESS  not-accessible
    STATUS      current
    DESCRIPTION
            "A list of all slot2Module's utilization."
    ::= { slot2Module 1 }  

slot2ModuleEntry OBJECT-TYPE
    SYNTAX      Slot2ModuleEntry
    MAX-ACCESS  not-accessible
    STATUS      current
    DESCRIPTION
            "An entry contains a slot2Module's utilization."
    INDEX   { slot2ModuleIndex }
    ::= { slot2ModuleTable 1 }

Slot2ModuleEntry ::=
    SEQUENCE {     
		slot2ModuleIndex                       Integer32,
		slot2ModuleId                           DisplayString,  
		slot2ModuleIfNumber                     Integer32		
    } 

slot2ModuleIndex OBJECT-TYPE
    SYNTAX      Integer32 (1..2147483647)
    MAX-ACCESS  not-accessible
    STATUS      current
    DESCRIPTION
            "A unique value, greater than zero, for each chassis`s slot2."
    ::= { slot2ModuleEntry 1 }

slot2ModuleId OBJECT-TYPE
    SYNTAX      DisplayString (SIZE (0..32))
    MAX-ACCESS  read-only
    STATUS      current
    DESCRIPTION
            "the value of module`s id"
    ::= { slot2ModuleEntry 2 }
  
slot2ModuleIfNumber OBJECT-TYPE
    SYNTAX      Integer32(0..2147483647)
    MAX-ACCESS  read-only
    STATUS      current
    DESCRIPTION
            "The number of network interfaces (regardless of their
            current state) present on this system." 
    ::= { slot2ModuleEntry 3 } 
    
slot2ModuleIfTable OBJECT-TYPE
    SYNTAX      SEQUENCE OF Slot2ModuleIfEntry
    MAX-ACCESS  not-accessible
    STATUS      current
    DESCRIPTION
            "A list of interface entries.  The number of entries is
            given by the value of ifNumber."
    ::= { slot2Module 2 } 
    
slot2ModuleIfEntry OBJECT-TYPE
    SYNTAX      Slot2ModuleIfEntry
    MAX-ACCESS  not-accessible
    STATUS      current
    DESCRIPTION
            "An entry containing management information applicable to a
            particular interface."
    INDEX   { slot2ModuleifIndex }
    ::= { slot2ModuleIfTable 1 }
    
Slot2ModuleIfEntry ::=
    SEQUENCE {
        slot2ModuleifIndex                 InterfaceIndex,  
        slot2ModuleIfId                    DisplayString,  
        slot2ModuleifDescr                 DisplayString,           
        slot2ModuleifType                  IANAifType,   		
        slot2ModuleifMtu                   Integer32,                
        slot2ModuleifSpeed                 Counter64,               
        slot2ModuleifPhysAddress           PhysAddress,              
        slot2ModuleifAdminStatus           INTEGER,                  
        slot2ModuleifOperStatus            INTEGER,                  
        slot2ModuleifLastChange            TimeTicks,                
        slot2ModuleifInOctets              Counter64,                
        slot2ModuleifInUcastPkts           Counter64,                
        slot2ModuleifInNUcastPkts          Counter64,   
        slot2ModuleifInDiscards            Counter64,
        slot2ModuleifInErrors              Counter64,
        slot2ModuleifInFcsErrorPkts        Counter64,
        slot2ModuleifInUnknownProtos       Counter64,	-- deprecated
        slot2ModuleifOutOctets             Counter64,
        slot2ModuleifOutUcastPkts          Counter64,
        slot2ModuleifOutNUcastPkts         Counter64,  -- deprecated
        slot2ModuleifOutDiscards           Counter64,
        slot2ModuleifOutErrors             Counter64,
        slot2ModuleifOutFcsErrorPkts       Counter64,
        slot2ModuleifOutQLen               Gauge32,    -- deprecated  
        slot2ModuleifOutOctetsRate         Counter64,
        slot2ModuleifInOctetsRate          Counter64,
        slot2ModuleifOutPktsRate           Counter64,
        slot2ModuleifInPktsRate            Counter64,
        slot2ModuleifRxPower               DisplayString,
        slot2ModuleifTxPower               DisplayString,
        slot2ModuleifSpecific              OBJECT IDENTIFIER,
        slot2ModuleifTxMirrorList          DisplayString,
        slot2ModuleifRxMirrorList          DisplayString,
        slot2ModuleifRxPowerMin               DisplayString,
        slot2ModuleifRxPowerMax               DisplayString,
        slot2ModuleifTxPowerMin               DisplayString,
        slot2ModuleifTxPowerMax               DisplayString,
        slot2ModuleifRxHisPeak            Counter64,
        slot2ModuleifTxHisPeak            Counter64,
        slot2ModuleifMode                 DisplayString   		
    }         

slot2ModuleifIndex OBJECT-TYPE
    SYNTAX      InterfaceIndex
    MAX-ACCESS  read-only
    STATUS      current
    DESCRIPTION
            "A unique value, greater than zero, for each interface.  It
            is recommended that values are assigned contiguously
            starting from 1.  The value for each interface sub-layer
            must remain constant at least from one re-initialization of
            the entity's network management system to the next re-
            initialization."
    ::= { slot2ModuleIfEntry 1 }
    
slot2ModuleIfId OBJECT-TYPE
    SYNTAX      DisplayString (SIZE (0..32))
    MAX-ACCESS  read-only
    STATUS      current
    DESCRIPTION
            "the value of module`s id"
    ::= { slot2ModuleIfEntry 2 }
    
slot2ModuleifDescr OBJECT-TYPE
    SYNTAX      DisplayString (SIZE (0..255))
    MAX-ACCESS  read-only
    STATUS      current
    DESCRIPTION
            "A textual string containing information about the
            interface.  This string should include the name of the
            manufacturer, the product name and the version of the
            interface hardware/software."
    ::= { slot2ModuleIfEntry 3 }
    
slot2ModuleifType OBJECT-TYPE
    SYNTAX      IANAifType
    MAX-ACCESS  read-only
    STATUS      current
    DESCRIPTION
            "The type of interface.  Additional values for ifType are
            assigned by the Internet Assigned Numbers Authority (IANA),
            through updating the syntax of the IANAifType textual
            convention."
    ::= { slot2ModuleIfEntry 4 }

slot2ModuleifMtu OBJECT-TYPE
    SYNTAX      Integer32(1..2147483647)
    MAX-ACCESS  read-only
    STATUS      current
    DESCRIPTION
            "The size of the largest packet which can be sent/received
            on the interface, specified in octets.  For interfaces that
            are used for transmitting network datagrams, this is the
            size of the largest network datagram that can be sent on the
            interface."
    ::= { slot2ModuleIfEntry 5 }

slot2ModuleifSpeed OBJECT-TYPE
    SYNTAX      Counter64
    MAX-ACCESS  read-only
    STATUS      current
    DESCRIPTION
            "An estimate of the interface's current bandwidth in bits
            per second.  For interfaces which do not vary in bandwidth
            or for those where no accurate estimation can be made, this
            object should contain the nominal bandwidth. For a sub-layer
            which has no concept of bandwidth, this object should be zero."
    ::= { slot2ModuleIfEntry 6 }

slot2ModuleifPhysAddress OBJECT-TYPE
    SYNTAX      PhysAddress
    MAX-ACCESS  read-only
    STATUS      current
    DESCRIPTION
            "The interface's address at its protocol sub-layer.  For
            example, for an 802.x interface, this object normally
            contains a MAC address.  The interface's media-specific MIB
            must define the bit and byte ordering and the format of the
            value of this object.  For interfaces which do not have such
            an address (e.g., a serial line), this object should contain
            an octet string of zero length."
    ::= { slot2ModuleIfEntry 7 }
    
slot2ModuleifAdminStatus OBJECT-TYPE
    SYNTAX  INTEGER {
                up(1),       -- ready to pass packets
                down(2),
                testing(3)   -- in some test mode
            }
    MAX-ACCESS  read-write
    STATUS      current
    DESCRIPTION
            "The desired state of the interface.  The testing(3) state
            indicates that no operational packets can be passed.  When a
            managed system initializes, all interfaces start with
            ifAdminStatus in the down(2) state.  As a result of either
            explicit management action or per configuration information
            retained by the managed system, ifAdminStatus is then
            changed to either the up(1) or testing(3) states (or remains
            in the down(2) state)."
    ::= { slot2ModuleIfEntry 8 }

slot2ModuleifOperStatus OBJECT-TYPE
    SYNTAX  INTEGER {
                up(1),        -- ready to pass packets
                down(2),
                testing(3),   -- in some test mode
                unknown(4),   -- status can not be determined
                              -- for some reason.
                dormant(5),
                notPresent(6),    -- some component is missing
                lowerLayerDown(7) -- down due to state of
                                  -- lower-layer interface(s)
            }
    MAX-ACCESS  read-only
    STATUS      current
    DESCRIPTION
            "The current operational state of the interface.  The
            testing(3) state indicates that no operational packets can
            be passed.  If ifAdminStatus is down(2) then ifOperStatus
            should be down(2).  If ifAdminStatus is changed to up(1)
            then ifOperStatus should change to up(1) if the interface is
            ready to transmit and receive network traffic; it should
            change to dormant(5) if the interface is waiting for
            external actions (such as a serial line waiting for an
            incoming connection); it should remain in the down(2) state
            if and only if there is a fault that prevents it from going
            to the up(1) state; it should remain in the notPresent(6)
            state if the interface has missing (typically, hardware)
            components."
    ::= { slot2ModuleIfEntry 9 }

slot2ModuleifLastChange OBJECT-TYPE
    SYNTAX      TimeTicks
    MAX-ACCESS  read-only
    STATUS      current
    DESCRIPTION
            "The value of sysUpTime at the time the interface entered
            its current operational state.  If the current state was
            entered prior to the last re-initialization of the local
            network management subsystem, then this object contains a
            zero value."
    ::= { slot2ModuleIfEntry 10 }

slot2ModuleifInOctets OBJECT-TYPE
    SYNTAX      Counter64
    MAX-ACCESS  read-only
    STATUS      current
    DESCRIPTION
            "The total number of octets received on the interface,
            including framing characters.

            Discontinuities in the value of this counter can occur at
            re-initialization of the management system, and at other
            times as indicated by the value of
            ifCounterDiscontinuityTime."
    ::= { slot2ModuleIfEntry 11 }

slot2ModuleifInUcastPkts OBJECT-TYPE
    SYNTAX      Counter64
    MAX-ACCESS  read-only
    STATUS      current
    DESCRIPTION
            "The number of packets, delivered by this sub-layer to a
            higher (sub-)layer, which were not addressed to a multicast
            or broadcast address at this sub-layer.

            Discontinuities in the value of this counter can occur at
            re-initialization of the management system, and at other
            times as indicated by the value of
            ifCounterDiscontinuityTime."
    ::= { slot2ModuleIfEntry 12 }

slot2ModuleifInNUcastPkts OBJECT-TYPE
    SYNTAX  Counter64
    MAX-ACCESS  read-only
    STATUS      current
    DESCRIPTION
            "The number of packets, delivered by this sub-layer to a
            higher (sub-)layer, which were addressed to a multicast or
            broadcast address at this sub-layer.

            Discontinuities in the value of this counter can occur at
            re-initialization of the management system, and at other
            times as indicated by the value of
            ifCounterDiscontinuityTime.

            This object is deprecated in favour of ifInMulticastPkts and
            ifInBroadcastPkts."
    ::= { slot2ModuleIfEntry 13 }

slot2ModuleifInDiscards OBJECT-TYPE
    SYNTAX      Counter64
    MAX-ACCESS  read-only
    STATUS      current
    DESCRIPTION
            "The number of inbound packets which were chosen to be
            discarded even though no errors had been detected to prevent

            their being deliverable to a higher-layer protocol.  One
            possible reason for discarding such a packet could be to
            free up buffer space.

            Discontinuities in the value of this counter can occur at
            re-initialization of the management system, and at other
            times as indicated by the value of
            ifCounterDiscontinuityTime."
    ::= { slot2ModuleIfEntry 14 }

slot2ModuleifInErrors OBJECT-TYPE
    SYNTAX      Counter64
    MAX-ACCESS  read-only
    STATUS      current
    DESCRIPTION
            "For packet-oriented interfaces, the number of inbound
            packets that contained errors preventing them from being
            deliverable to a higher-layer protocol.  For character-
            oriented or fixed-length interfaces, the number of inbound
            transmission units that contained errors preventing them
            from being deliverable to a higher-layer protocol.

            Discontinuities in the value of this counter can occur at
            re-initialization of the management system, and at other
            times as indicated by the value of
            ifCounterDiscontinuityTime."
    ::= { slot2ModuleIfEntry 15 }

slot2ModuleifInFcsErrorPkts OBJECT-TYPE
    SYNTAX      Counter64
    MAX-ACCESS  read-only
    STATUS      current
    DESCRIPTION
            "FCS error pakets."
    ::= { slot2ModuleIfEntry 16 }

slot2ModuleifInUnknownProtos OBJECT-TYPE
    SYNTAX      Counter64
    MAX-ACCESS  read-only
    STATUS      current
    DESCRIPTION
            "For packet-oriented interfaces, the number of packets
            received via the interface which were discarded because of
            an unknown or unsupported protocol.  For character-oriented
            or fixed-length interfaces that support protocol
            multiplexing the number of transmission units received via
            the interface which were discarded because of an unknown or
            unsupported protocol.  For any interface that does not
            support protocol multiplexing, this counter will always be
            0.

            Discontinuities in the value of this counter can occur at
            re-initialization of the management system, and at other
            times as indicated by the value of
            ifCounterDiscontinuityTime."
    ::= { slot2ModuleIfEntry 17 }

slot2ModuleifOutOctets OBJECT-TYPE
    SYNTAX      Counter64
    MAX-ACCESS  read-only
    STATUS      current
    DESCRIPTION
            "The total number of octets transmitted out of the
            interface, including framing characters.

            Discontinuities in the value of this counter can occur at
            re-initialization of the management system, and at other
            times as indicated by the value of
            ifCounterDiscontinuityTime."
    ::= { slot2ModuleIfEntry 18 }

slot2ModuleifOutUcastPkts OBJECT-TYPE
    SYNTAX      Counter64
    MAX-ACCESS  read-only
    STATUS      current
    DESCRIPTION
            "The total number of packets that higher-level protocols
            requested be transmitted, and which were not addressed to a
            multicast or broadcast address at this sub-layer, including
            those that were discarded or not sent.

            Discontinuities in the value of this counter can occur at
            re-initialization of the management system, and at other
            times as indicated by the value of
            ifCounterDiscontinuityTime."
    ::= { slot2ModuleIfEntry 19 }

slot2ModuleifOutNUcastPkts OBJECT-TYPE
    SYNTAX      Counter64
    MAX-ACCESS  read-only
    STATUS      deprecated
    DESCRIPTION
            "The total number of packets that higher-level protocols
            requested be transmitted, and which were addressed to a
            multicast or broadcast address at this sub-layer, including
            those that were discarded or not sent.

            Discontinuities in the value of this counter can occur at
            re-initialization of the management system, and at other
            times as indicated by the value of
            ifCounterDiscontinuityTime.

            This object is deprecated in favour of ifOutMulticastPkts
            and ifOutBroadcastPkts."
    ::= { slot2ModuleIfEntry 20 }

slot2ModuleifOutDiscards OBJECT-TYPE
    SYNTAX      Counter64
    MAX-ACCESS  read-only
    STATUS      current
    DESCRIPTION
            "The number of outbound packets which were chosen to be
            discarded even though no errors had been detected to prevent
            their being transmitted.  One possible reason for discarding
            such a packet could be to free up buffer space.

            Discontinuities in the value of this counter can occur at
            re-initialization of the management system, and at other
            times as indicated by the value of
            ifCounterDiscontinuityTime."
    ::= { slot2ModuleIfEntry 21 }

slot2ModuleifOutErrors OBJECT-TYPE
    SYNTAX      Counter64
    MAX-ACCESS  read-only
    STATUS      current
    DESCRIPTION
            "For packet-oriented interfaces, the number of outbound
            packets that could not be transmitted because of errors.
            For character-oriented or fixed-length interfaces, the
            number of outbound transmission units that could not be
            transmitted because of errors.

            Discontinuities in the value of this counter can occur at
            re-initialization of the management system, and at other
            times as indicated by the value of
            ifCounterDiscontinuityTime."
    ::= { slot2ModuleIfEntry 22 }

slot2ModuleifOutFcsErrorPkts OBJECT-TYPE
    SYNTAX      Counter64
    MAX-ACCESS  read-only
    STATUS      current
    DESCRIPTION
            "FCS error pakets."
    ::= { slot2ModuleIfEntry 23 }

slot2ModuleifOutQLen OBJECT-TYPE
    SYNTAX      Gauge32
    MAX-ACCESS  read-only
    STATUS      deprecated
    DESCRIPTION
            "The length of the output packet queue (in packets)."
    ::= { slot2ModuleIfEntry 24 }

slot2ModuleifOutOctetsRate OBJECT-TYPE
    SYNTAX      Counter64
    MAX-ACCESS  read-only
    STATUS      current
    DESCRIPTION
            "The speed of octets trans on the interface(kbps)"
    ::= { slot2ModuleIfEntry 25 }

slot2ModuleifInOctetsRate OBJECT-TYPE
    SYNTAX      Counter64
    MAX-ACCESS  read-only
    STATUS      current
    DESCRIPTION
            "The speed of octets received on the interface(kbps)"
    ::= { slot2ModuleIfEntry 26 }

slot2ModuleifOutPktsRate OBJECT-TYPE
    SYNTAX      Counter64
    MAX-ACCESS  read-only
    STATUS      current
    DESCRIPTION
            "The speed of packets trans on the interface(pps)"
    ::= { slot2ModuleIfEntry 27 }

slot2ModuleifInPktsRate OBJECT-TYPE
    SYNTAX      Counter64
    MAX-ACCESS  read-only
    STATUS      current
    DESCRIPTION
            "The speed of octets received on the interface(kbps)"
    ::= { slot2ModuleIfEntry 28 }

slot2ModuleifRxPower OBJECT-TYPE
    SYNTAX      DisplayString (SIZE (0..255))
    MAX-ACCESS  read-only
    STATUS      current
    DESCRIPTION
            "the value of interface's received power, in dbm format."
    ::= { slot2ModuleIfEntry 29 }

slot2ModuleifTxPower OBJECT-TYPE
    SYNTAX      DisplayString (SIZE (0..255))
    MAX-ACCESS  read-only
    STATUS      current
    DESCRIPTION
            "the value of interface's send power, in dbm format."
    ::= { slot2ModuleIfEntry 30 }


slot2ModuleifSpecific OBJECT-TYPE
    SYNTAX      OBJECT IDENTIFIER
    MAX-ACCESS  read-only
    STATUS      deprecated
    DESCRIPTION
            "A reference to MIB definitions specific to the particular
            media being used to realize the interface.  It is

            recommended that this value point to an instance of a MIB
            object in the media-specific MIB, i.e., that this object
            have the semantics associated with the InstancePointer
            textual convention defined in RFC 2579.  In fact, it is
            recommended that the media-specific MIB specify what value
            ifSpecific should/can take for values of ifType.  If no MIB
            definitions specific to the particular media are available,
            the value should be set to the OBJECT IDENTIFIER { 0 0 }."
    ::= { slot2ModuleIfEntry 31 }  
  
slot2ModuleifTxMirrorList OBJECT-TYPE
    SYNTAX      DisplayString (SIZE (0..255))
    MAX-ACCESS  read-only
    STATUS      deprecated
    DESCRIPTION
            "the interface tx mirror list."
    ::= { slot2ModuleIfEntry 32 }  
 
slot2ModuleifRxMirrorList OBJECT-TYPE
    SYNTAX      DisplayString (SIZE (0..255))
    MAX-ACCESS  read-only
    STATUS      deprecated
    DESCRIPTION
            "the interface rx mirror list."
    ::= { slot2ModuleIfEntry 33 }  
  
slot2ModuleifRxPowerMin OBJECT-TYPE
    SYNTAX      DisplayString (SIZE (0..255))
    MAX-ACCESS  read-only
    STATUS      deprecated
    DESCRIPTION
            "the interface min rx power."
    ::= { slot2ModuleIfEntry 34 }  

slot2ModuleifRxPowerMax OBJECT-TYPE
    SYNTAX      DisplayString (SIZE (0..255))
    MAX-ACCESS  read-only
    STATUS      deprecated
    DESCRIPTION
            "the interface max rx power."
    ::= { slot2ModuleIfEntry 35 }  

slot2ModuleifTxPowerMin OBJECT-TYPE
    SYNTAX      DisplayString (SIZE (0..255))
    MAX-ACCESS  read-only
    STATUS      deprecated
    DESCRIPTION
            "the interface min tx power."
    ::= { slot2ModuleIfEntry 36 }  

slot2ModuleifTxPowerMax OBJECT-TYPE
    SYNTAX      DisplayString (SIZE (0..255))
    MAX-ACCESS  read-only
    STATUS      deprecated
    DESCRIPTION
            "the interface max tx power."
    ::= { slot2ModuleIfEntry 37 }  

slot2ModuleifRxHisPeak OBJECT-TYPE
    SYNTAX      Counter64
    MAX-ACCESS  read-only
    STATUS      current
    DESCRIPTION
            "The max speed of rx rate on the interface(kbps)"
    ::= { slot2ModuleIfEntry 38 }

slot2ModuleifTxHisPeak OBJECT-TYPE
    SYNTAX      Counter64
    MAX-ACCESS  read-only
    STATUS      current
    DESCRIPTION
            "The max speed of tx rate on the interface(kbps)"
    ::= { slot2ModuleIfEntry 39 }

slot2ModuleifMode OBJECT-TYPE
    SYNTAX      DisplayString (SIZE (0..255))
    MAX-ACCESS  read-only
    STATUS      deprecated
    DESCRIPTION
            "the interface if mode."
    ::= { slot2ModuleIfEntry 40 }  

-- slot 3 --

-- slot3Table --

slot3Table OBJECT-TYPE
    SYNTAX      SEQUENCE OF Slot3Entry
    MAX-ACCESS  not-accessible
    STATUS      current
    DESCRIPTION
            "A list of all slot3Type's utilization."
    ::= { slot3 1 }  

slot3Entry OBJECT-TYPE
    SYNTAX      Slot3Entry
    MAX-ACCESS  not-accessible
    STATUS      current
    DESCRIPTION
            "An entry contains a slot3's utilization."
    INDEX   { slot3Index }
    ::= { slot3Table 1 }

Slot3Entry ::=
    SEQUENCE {     
		slot3Index                       Integer32,
		slot3Type                        DisplayString,
		slot3Status                      DisplayString,		
        slot3SerialNumber                DisplayString,		
        slot3Temperature                 DisplayString
    }  

slot3Index OBJECT-TYPE
    SYNTAX      Integer32 (1..2147483647)
    MAX-ACCESS  not-accessible
    STATUS      current
    DESCRIPTION
            "A unique value, greater than zero, for each chassis`s slot3."
    ::= { slot3Entry 1 }

slot3Type OBJECT-TYPE
    SYNTAX      DisplayString (SIZE (0..255))
    MAX-ACCESS  read-only
    STATUS      current
    DESCRIPTION
            "the slot3Type of each chassis."
    ::= { slot3Entry 2 }

slot3Status OBJECT-TYPE
    SYNTAX      DisplayString (SIZE (0..255))
    MAX-ACCESS  read-only
    STATUS      current
    DESCRIPTION
            "A string to describe the board status." 
    ::= { slot3Entry 3 }   


slot3SerialNumber OBJECT-TYPE
    SYNTAX      DisplayString (SIZE (0..255))
    MAX-ACCESS  read-only
    STATUS      current
    DESCRIPTION
            "A string to describe the board serial number." 
    ::= { slot3Entry 4 }   

slot3Temperature OBJECT-TYPE
    SYNTAX      DisplayString (SIZE (0..255))
    MAX-ACCESS  read-only
    STATUS      current
    DESCRIPTION
            "A string to describe the board temperature." 
    ::= { slot3Entry 5 }   


slot3Module OBJECT IDENTIFIER ::= { slot3 2 }

-- slot3ModuleTable --
slot3ModuleTable OBJECT-TYPE
    SYNTAX      SEQUENCE OF Slot3ModuleEntry
    MAX-ACCESS  not-accessible
    STATUS      current
    DESCRIPTION
            "A list of all slot3Module's utilization."
    ::= { slot3Module 1 }  

slot3ModuleEntry OBJECT-TYPE
    SYNTAX      Slot3ModuleEntry
    MAX-ACCESS  not-accessible
    STATUS      current
    DESCRIPTION
            "An entry contains a slot3Module's utilization."
    INDEX   { slot3ModuleIndex }
    ::= { slot3ModuleTable 1 }

Slot3ModuleEntry ::=
    SEQUENCE {     
		slot3ModuleIndex                       Integer32,
		slot3ModuleId                           DisplayString,  
		slot3ModuleIfNumber                     Integer32		
    } 

slot3ModuleIndex OBJECT-TYPE
    SYNTAX      Integer32 (1..2147483647)
    MAX-ACCESS  not-accessible
    STATUS      current
    DESCRIPTION
            "A unique value, greater than zero, for each chassis`s slot3."
    ::= { slot3ModuleEntry 1 }

slot3ModuleId OBJECT-TYPE
    SYNTAX      DisplayString (SIZE (0..32))
    MAX-ACCESS  read-only
    STATUS      current
    DESCRIPTION
            "the value of module`s id"
    ::= { slot3ModuleEntry 2 }
  
slot3ModuleIfNumber OBJECT-TYPE
    SYNTAX      Integer32(0..2147483647)
    MAX-ACCESS  read-only
    STATUS      current
    DESCRIPTION
            "The number of network interfaces (regardless of their
            current state) present on this system." 
    ::= { slot3ModuleEntry 3 } 
    
slot3ModuleIfTable OBJECT-TYPE
    SYNTAX      SEQUENCE OF Slot3ModuleIfEntry
    MAX-ACCESS  not-accessible
    STATUS      current
    DESCRIPTION
            "A list of interface entries.  The number of entries is
            given by the value of ifNumber."
    ::= { slot3Module 2 } 
    
slot3ModuleIfEntry OBJECT-TYPE
    SYNTAX      Slot3ModuleIfEntry
    MAX-ACCESS  not-accessible
    STATUS      current
    DESCRIPTION
            "An entry containing management information applicable to a
            particular interface."
    INDEX   { slot3ModuleifIndex }
    ::= { slot3ModuleIfTable 1 }
    
Slot3ModuleIfEntry ::=
    SEQUENCE {
        slot3ModuleifIndex                 InterfaceIndex,  
        slot3ModuleIfId                    DisplayString,  
        slot3ModuleifDescr                 DisplayString,           
        slot3ModuleifType                  IANAifType,   		
        slot3ModuleifMtu                   Integer32,                
        slot3ModuleifSpeed                 Counter64,               
        slot3ModuleifPhysAddress           PhysAddress,              
        slot3ModuleifAdminStatus           INTEGER,                  
        slot3ModuleifOperStatus            INTEGER,                  
        slot3ModuleifLastChange            TimeTicks,                
        slot3ModuleifInOctets              Counter64,                
        slot3ModuleifInUcastPkts           Counter64,                
        slot3ModuleifInNUcastPkts          Counter64,    
        slot3ModuleifInDiscards            Counter64,
        slot3ModuleifInErrors              Counter64,
        slot3ModuleifInFcsErrorPkts        Counter64,
        slot3ModuleifInUnknownProtos       Counter64,	-- deprecated
        slot3ModuleifOutOctets             Counter64,
        slot3ModuleifOutUcastPkts          Counter64,
        slot3ModuleifOutNUcastPkts         Counter64,  -- deprecated
        slot3ModuleifOutDiscards           Counter64,
        slot3ModuleifOutErrors             Counter64,
        slot3ModuleifOutFcsErrorPkts       Counter64,
        slot3ModuleifOutQLen               Gauge32,    -- deprecated  
        slot3ModuleifOutOctetsRate         Counter64,
        slot3ModuleifInOctetsRate          Counter64,
        slot3ModuleifOutPktsRate           Counter64,
        slot3ModuleifInPktsRate            Counter64,
        slot3ModuleifRxPower               DisplayString,
        slot3ModuleifTxPower               DisplayString,
        slot3ModuleifSpecific              OBJECT IDENTIFIER,
        slot3ModuleifTxMirrorList          DisplayString,
        slot3ModuleifRxMirrorList          DisplayString,
        slot3ModuleifRxPowerMin               DisplayString,
        slot3ModuleifRxPowerMax               DisplayString,
        slot3ModuleifTxPowerMin               DisplayString,
        slot3ModuleifTxPowerMax               DisplayString,
        slot3ModuleifRxHisPeak            Counter64,
        slot3ModuleifTxHisPeak            Counter64,
        slot3ModuleifMode                 DisplayString   		
    }         

slot3ModuleifIndex OBJECT-TYPE
    SYNTAX      InterfaceIndex
    MAX-ACCESS  read-only
    STATUS      current
    DESCRIPTION
            "A unique value, greater than zero, for each interface.  It
            is recommended that values are assigned contiguously
            starting from 1.  The value for each interface sub-layer
            must remain constant at least from one re-initialization of
            the entity's network management system to the next re-
            initialization."
    ::= { slot3ModuleIfEntry 1 }
    
slot3ModuleIfId OBJECT-TYPE
    SYNTAX      DisplayString (SIZE (0..32))
    MAX-ACCESS  read-only
    STATUS      current
    DESCRIPTION
            "the value of module`s id"
    ::= { slot3ModuleIfEntry 2 }
    
slot3ModuleifDescr OBJECT-TYPE
    SYNTAX      DisplayString (SIZE (0..255))
    MAX-ACCESS  read-only
    STATUS      current
    DESCRIPTION
            "A textual string containing information about the
            interface.  This string should include the name of the
            manufacturer, the product name and the version of the
            interface hardware/software."
    ::= { slot3ModuleIfEntry 3 }
    
slot3ModuleifType OBJECT-TYPE
    SYNTAX      IANAifType
    MAX-ACCESS  read-only
    STATUS      current
    DESCRIPTION
            "The type of interface.  Additional values for ifType are
            assigned by the Internet Assigned Numbers Authority (IANA),
            through updating the syntax of the IANAifType textual
            convention."
    ::= { slot3ModuleIfEntry 4 }

slot3ModuleifMtu OBJECT-TYPE
    SYNTAX      Integer32(1..2147483647)
    MAX-ACCESS  read-only
    STATUS      current
    DESCRIPTION
            "The size of the largest packet which can be sent/received
            on the interface, specified in octets.  For interfaces that
            are used for transmitting network datagrams, this is the
            size of the largest network datagram that can be sent on the
            interface."
    ::= { slot3ModuleIfEntry 5 }

slot3ModuleifSpeed OBJECT-TYPE
    SYNTAX      Counter64
    MAX-ACCESS  read-only
    STATUS      current
    DESCRIPTION
            "An estimate of the interface's current bandwidth in bits
            per second.  For interfaces which do not vary in bandwidth
            or for those where no accurate estimation can be made, this
            object should contain the nominal bandwidth. For a sub-layer
            which has no concept of bandwidth, this object should be zero."
    ::= { slot3ModuleIfEntry 6 }

slot3ModuleifPhysAddress OBJECT-TYPE
    SYNTAX      PhysAddress
    MAX-ACCESS  read-only
    STATUS      current
    DESCRIPTION
            "The interface's address at its protocol sub-layer.  For
            example, for an 802.x interface, this object normally
            contains a MAC address.  The interface's media-specific MIB
            must define the bit and byte ordering and the format of the
            value of this object.  For interfaces which do not have such
            an address (e.g., a serial line), this object should contain
            an octet string of zero length."
    ::= { slot3ModuleIfEntry 7 }
    
slot3ModuleifAdminStatus OBJECT-TYPE
    SYNTAX  INTEGER {
                up(1),       -- ready to pass packets
                down(2),
                testing(3)   -- in some test mode
            }
    MAX-ACCESS  read-write
    STATUS      current
    DESCRIPTION
            "The desired state of the interface.  The testing(3) state
            indicates that no operational packets can be passed.  When a
            managed system initializes, all interfaces start with
            ifAdminStatus in the down(2) state.  As a result of either
            explicit management action or per configuration information
            retained by the managed system, ifAdminStatus is then
            changed to either the up(1) or testing(3) states (or remains
            in the down(2) state)."
    ::= { slot3ModuleIfEntry 8 }

slot3ModuleifOperStatus OBJECT-TYPE
    SYNTAX  INTEGER {
                up(1),        -- ready to pass packets
                down(2),
                testing(3),   -- in some test mode
                unknown(4),   -- status can not be determined
                              -- for some reason.
                dormant(5),
                notPresent(6),    -- some component is missing
                lowerLayerDown(7) -- down due to state of
                                  -- lower-layer interface(s)
            }
    MAX-ACCESS  read-only
    STATUS      current
    DESCRIPTION
            "The current operational state of the interface.  The
            testing(3) state indicates that no operational packets can
            be passed.  If ifAdminStatus is down(2) then ifOperStatus
            should be down(2).  If ifAdminStatus is changed to up(1)
            then ifOperStatus should change to up(1) if the interface is
            ready to transmit and receive network traffic; it should
            change to dormant(5) if the interface is waiting for
            external actions (such as a serial line waiting for an
            incoming connection); it should remain in the down(2) state
            if and only if there is a fault that prevents it from going
            to the up(1) state; it should remain in the notPresent(6)
            state if the interface has missing (typically, hardware)
            components."
    ::= { slot3ModuleIfEntry 9 }

slot3ModuleifLastChange OBJECT-TYPE
    SYNTAX      TimeTicks
    MAX-ACCESS  read-only
    STATUS      current
    DESCRIPTION
            "The value of sysUpTime at the time the interface entered
            its current operational state.  If the current state was
            entered prior to the last re-initialization of the local
            network management subsystem, then this object contains a
            zero value."
    ::= { slot3ModuleIfEntry 10 }

slot3ModuleifInOctets OBJECT-TYPE
    SYNTAX      Counter64
    MAX-ACCESS  read-only
    STATUS      current
    DESCRIPTION
            "The total number of octets received on the interface,
            including framing characters.

            Discontinuities in the value of this counter can occur at
            re-initialization of the management system, and at other
            times as indicated by the value of
            ifCounterDiscontinuityTime."
    ::= { slot3ModuleIfEntry 11 }

slot3ModuleifInUcastPkts OBJECT-TYPE
    SYNTAX      Counter64
    MAX-ACCESS  read-only
    STATUS      current
    DESCRIPTION
            "The number of packets, delivered by this sub-layer to a
            higher (sub-)layer, which were not addressed to a multicast
            or broadcast address at this sub-layer.

            Discontinuities in the value of this counter can occur at
            re-initialization of the management system, and at other
            times as indicated by the value of
            ifCounterDiscontinuityTime."
    ::= { slot3ModuleIfEntry 12 }

slot3ModuleifInNUcastPkts OBJECT-TYPE
    SYNTAX  Counter64
    MAX-ACCESS  read-only
    STATUS      current
    DESCRIPTION
            "The number of packets, delivered by this sub-layer to a
            higher (sub-)layer, which were addressed to a multicast or
            broadcast address at this sub-layer.

            Discontinuities in the value of this counter can occur at
            re-initialization of the management system, and at other
            times as indicated by the value of
            ifCounterDiscontinuityTime.

            This object is deprecated in favour of ifInMulticastPkts and
            ifInBroadcastPkts."
    ::= { slot3ModuleIfEntry 13 }

slot3ModuleifInDiscards OBJECT-TYPE
    SYNTAX      Counter64
    MAX-ACCESS  read-only
    STATUS      current
    DESCRIPTION
            "The number of inbound packets which were chosen to be
            discarded even though no errors had been detected to prevent

            their being deliverable to a higher-layer protocol.  One
            possible reason for discarding such a packet could be to
            free up buffer space.

            Discontinuities in the value of this counter can occur at
            re-initialization of the management system, and at other
            times as indicated by the value of
            ifCounterDiscontinuityTime."
    ::= { slot3ModuleIfEntry 14 }

slot3ModuleifInErrors OBJECT-TYPE
    SYNTAX      Counter64
    MAX-ACCESS  read-only
    STATUS      current
    DESCRIPTION
            "For packet-oriented interfaces, the number of inbound
            packets that contained errors preventing them from being
            deliverable to a higher-layer protocol.  For character-
            oriented or fixed-length interfaces, the number of inbound
            transmission units that contained errors preventing them
            from being deliverable to a higher-layer protocol.

            Discontinuities in the value of this counter can occur at
            re-initialization of the management system, and at other
            times as indicated by the value of
            ifCounterDiscontinuityTime."
    ::= { slot3ModuleIfEntry 15 }

slot3ModuleifInFcsErrorPkts OBJECT-TYPE
    SYNTAX      Counter64
    MAX-ACCESS  read-only
    STATUS      current
    DESCRIPTION
            "FCS error pakets."
    ::= { slot3ModuleIfEntry 16 }

slot3ModuleifInUnknownProtos OBJECT-TYPE
    SYNTAX      Counter64
    MAX-ACCESS  read-only
    STATUS      current
    DESCRIPTION
            "For packet-oriented interfaces, the number of packets
            received via the interface which were discarded because of
            an unknown or unsupported protocol.  For character-oriented
            or fixed-length interfaces that support protocol
            multiplexing the number of transmission units received via
            the interface which were discarded because of an unknown or
            unsupported protocol.  For any interface that does not
            support protocol multiplexing, this counter will always be
            0.

            Discontinuities in the value of this counter can occur at
            re-initialization of the management system, and at other
            times as indicated by the value of
            ifCounterDiscontinuityTime."
    ::= { slot3ModuleIfEntry 17 }

slot3ModuleifOutOctets OBJECT-TYPE
    SYNTAX      Counter64
    MAX-ACCESS  read-only
    STATUS      current
    DESCRIPTION
            "The total number of octets transmitted out of the
            interface, including framing characters.

            Discontinuities in the value of this counter can occur at
            re-initialization of the management system, and at other
            times as indicated by the value of
            ifCounterDiscontinuityTime."
    ::= { slot3ModuleIfEntry 18 }

slot3ModuleifOutUcastPkts OBJECT-TYPE
    SYNTAX      Counter64
    MAX-ACCESS  read-only
    STATUS      current
    DESCRIPTION
            "The total number of packets that higher-level protocols
            requested be transmitted, and which were not addressed to a
            multicast or broadcast address at this sub-layer, including
            those that were discarded or not sent.

            Discontinuities in the value of this counter can occur at
            re-initialization of the management system, and at other
            times as indicated by the value of
            ifCounterDiscontinuityTime."
    ::= { slot3ModuleIfEntry 19 }

slot3ModuleifOutNUcastPkts OBJECT-TYPE
    SYNTAX      Counter64
    MAX-ACCESS  read-only
    STATUS      deprecated
    DESCRIPTION
            "The total number of packets that higher-level protocols
            requested be transmitted, and which were addressed to a
            multicast or broadcast address at this sub-layer, including
            those that were discarded or not sent.

            Discontinuities in the value of this counter can occur at
            re-initialization of the management system, and at other
            times as indicated by the value of
            ifCounterDiscontinuityTime.

            This object is deprecated in favour of ifOutMulticastPkts
            and ifOutBroadcastPkts."
    ::= { slot3ModuleIfEntry 20 }

slot3ModuleifOutDiscards OBJECT-TYPE
    SYNTAX      Counter64
    MAX-ACCESS  read-only
    STATUS      current
    DESCRIPTION
            "The number of outbound packets which were chosen to be
            discarded even though no errors had been detected to prevent
            their being transmitted.  One possible reason for discarding
            such a packet could be to free up buffer space.

            Discontinuities in the value of this counter can occur at
            re-initialization of the management system, and at other
            times as indicated by the value of
            ifCounterDiscontinuityTime."
    ::= { slot3ModuleIfEntry 21 }

slot3ModuleifOutErrors OBJECT-TYPE
    SYNTAX      Counter64
    MAX-ACCESS  read-only
    STATUS      current
    DESCRIPTION
            "For packet-oriented interfaces, the number of outbound
            packets that could not be transmitted because of errors.
            For character-oriented or fixed-length interfaces, the
            number of outbound transmission units that could not be
            transmitted because of errors.

            Discontinuities in the value of this counter can occur at
            re-initialization of the management system, and at other
            times as indicated by the value of
            ifCounterDiscontinuityTime."
    ::= { slot3ModuleIfEntry 22 }

slot3ModuleifOutFcsErrorPkts OBJECT-TYPE
    SYNTAX      Counter64
    MAX-ACCESS  read-only
    STATUS      current
    DESCRIPTION
            "FCS error pakets."
    ::= { slot3ModuleIfEntry 23 }

slot3ModuleifOutQLen OBJECT-TYPE
    SYNTAX      Gauge32
    MAX-ACCESS  read-only
    STATUS      deprecated
    DESCRIPTION
            "The length of the output packet queue (in packets)."
    ::= { slot3ModuleIfEntry 24 }

slot3ModuleifOutOctetsRate OBJECT-TYPE
    SYNTAX      Counter64
    MAX-ACCESS  read-only
    STATUS      current
    DESCRIPTION
            "The speed of octets trans on the interface(kbps)"
    ::= { slot3ModuleIfEntry 25 }

slot3ModuleifInOctetsRate OBJECT-TYPE
    SYNTAX      Counter64
    MAX-ACCESS  read-only
    STATUS      current
    DESCRIPTION
            "The speed of octets received on the interface(kbps)"
    ::= { slot3ModuleIfEntry 26 }

slot3ModuleifOutPktsRate OBJECT-TYPE
    SYNTAX      Counter64
    MAX-ACCESS  read-only
    STATUS      current
    DESCRIPTION
            "The speed of packets trans on the interface(pps)"
    ::= { slot3ModuleIfEntry 27 }

slot3ModuleifInPktsRate OBJECT-TYPE
    SYNTAX      Counter64
    MAX-ACCESS  read-only
    STATUS      current
    DESCRIPTION
            "The speed of octets received on the interface(kbps)"
    ::= { slot3ModuleIfEntry 28 }

slot3ModuleifRxPower OBJECT-TYPE
    SYNTAX      DisplayString (SIZE (0..255))
    MAX-ACCESS  read-only
    STATUS      current
    DESCRIPTION
            "the value of interface's received power, in dbm format."
    ::= { slot3ModuleIfEntry 29 }

slot3ModuleifTxPower OBJECT-TYPE
    SYNTAX      DisplayString (SIZE (0..255))
    MAX-ACCESS  read-only
    STATUS      current
    DESCRIPTION
            "the value of interface's send power, in dbm format."
    ::= { slot3ModuleIfEntry 30 }

slot3ModuleifSpecific OBJECT-TYPE
    SYNTAX      OBJECT IDENTIFIER
    MAX-ACCESS  read-only
    STATUS      deprecated
    DESCRIPTION
            "A reference to MIB definitions specific to the particular
            media being used to realize the interface.  It is

            recommended that this value point to an instance of a MIB
            object in the media-specific MIB, i.e., that this object
            have the semantics associated with the InstancePointer
            textual convention defined in RFC 2579.  In fact, it is
            recommended that the media-specific MIB specify what value
            ifSpecific should/can take for values of ifType.  If no MIB
            definitions specific to the particular media are available,
            the value should be set to the OBJECT IDENTIFIER { 0 0 }."
    ::= { slot3ModuleIfEntry 31 }  
  
slot3ModuleifTxMirrorList OBJECT-TYPE
    SYNTAX      DisplayString (SIZE (0..255)) 
    MAX-ACCESS  read-only
    STATUS      deprecated
    DESCRIPTION
            "the interface tx mirror list."
    ::= { slot3ModuleIfEntry 32 }  
 
slot3ModuleifRxMirrorList OBJECT-TYPE
    SYNTAX      DisplayString (SIZE (0..255))
    MAX-ACCESS  read-only
    STATUS      deprecated
    DESCRIPTION
            "the interface rx mirror list."
    ::= { slot3ModuleIfEntry 33 }  

slot3ModuleifRxPowerMin OBJECT-TYPE
    SYNTAX      DisplayString (SIZE (0..255))
    MAX-ACCESS  read-only
    STATUS      deprecated
    DESCRIPTION
            "the interface min rx power."
    ::= { slot3ModuleIfEntry 34 }  

slot3ModuleifRxPowerMax OBJECT-TYPE
    SYNTAX      DisplayString (SIZE (0..255))
    MAX-ACCESS  read-only
    STATUS      deprecated
    DESCRIPTION
            "the interface max rx power."
    ::= { slot3ModuleIfEntry 35 }  

slot3ModuleifTxPowerMin OBJECT-TYPE
    SYNTAX      DisplayString (SIZE (0..255))
    MAX-ACCESS  read-only
    STATUS      deprecated
    DESCRIPTION
            "the interface min tx power."
    ::= { slot3ModuleIfEntry 36 }  

slot3ModuleifTxPowerMax OBJECT-TYPE
    SYNTAX      DisplayString (SIZE (0..255))
    MAX-ACCESS  read-only
    STATUS      deprecated
    DESCRIPTION
            "the interface max tx power."
    ::= { slot3ModuleIfEntry 37 }  

slot3ModuleifRxHisPeak OBJECT-TYPE
    SYNTAX      Counter64
    MAX-ACCESS  read-only
    STATUS      current
    DESCRIPTION
            "The max speed of rx rate on the interface(kbps)"
    ::= { slot3ModuleIfEntry 38 }

slot3ModuleifTxHisPeak OBJECT-TYPE
    SYNTAX      Counter64
    MAX-ACCESS  read-only
    STATUS      current
    DESCRIPTION
            "The max speed of tx rate on the interface(kbps)"
    ::= { slot3ModuleIfEntry 39 }

slot3ModuleifMode OBJECT-TYPE
    SYNTAX      DisplayString (SIZE (0..255))
    MAX-ACCESS  read-only
    STATUS      deprecated
    DESCRIPTION
            "the interface if mode."
    ::= { slot3ModuleIfEntry 40 }  

-- slot 4 --

-- slot4Table --

slot4Table OBJECT-TYPE
    SYNTAX      SEQUENCE OF Slot4Entry
    MAX-ACCESS  not-accessible
    STATUS      current
    DESCRIPTION
            "A list of all slot4Type's utilization."
    ::= { slot4 1 }  

slot4Entry OBJECT-TYPE
    SYNTAX      Slot4Entry
    MAX-ACCESS  not-accessible
    STATUS      current
    DESCRIPTION
            "An entry contains a slot4's utilization."
    INDEX   { slot4Index }
    ::= { slot4Table 1 }

Slot4Entry ::=
    SEQUENCE {     
		slot4Index                       Integer32,
		slot4Type                        DisplayString,
		slot4Status                      DisplayString,		
        slot4SerialNumber                DisplayString,		
        slot4Temperature                 DisplayString
    }  

slot4Index OBJECT-TYPE
    SYNTAX      Integer32 (1..2147483647)
    MAX-ACCESS  not-accessible
    STATUS      current
    DESCRIPTION
            "A unique value, greater than zero, for each chassis`s slot4."
    ::= { slot4Entry 1 }

slot4Type OBJECT-TYPE
    SYNTAX      DisplayString (SIZE (0..255))
    MAX-ACCESS  read-only
    STATUS      current
    DESCRIPTION
            "the slot4Type of each chassis."
    ::= { slot4Entry 2 }

slot4Status OBJECT-TYPE
    SYNTAX      DisplayString (SIZE (0..255))
    MAX-ACCESS  read-only
    STATUS      current
    DESCRIPTION
            "A string to describe the board status." 
    ::= { slot4Entry 3 }   

slot4SerialNumber OBJECT-TYPE
    SYNTAX      DisplayString (SIZE (0..255))
    MAX-ACCESS  read-only
    STATUS      current
    DESCRIPTION
            "A string to describe the board serial number." 
    ::= { slot4Entry 4 }   

slot4Temperature OBJECT-TYPE
    SYNTAX      DisplayString (SIZE (0..255))
    MAX-ACCESS  read-only
    STATUS      current
    DESCRIPTION
            "A string to describe the board temperature." 
    ::= { slot4Entry 5 }   


slot4Module OBJECT IDENTIFIER ::= { slot4 2 }

-- slot4ModuleTable --
slot4ModuleTable OBJECT-TYPE
    SYNTAX      SEQUENCE OF Slot4ModuleEntry
    MAX-ACCESS  not-accessible
    STATUS      current
    DESCRIPTION
            "A list of all slot4Module's utilization."
    ::= { slot4Module 1 }  

slot4ModuleEntry OBJECT-TYPE
    SYNTAX      Slot4ModuleEntry
    MAX-ACCESS  not-accessible
    STATUS      current
    DESCRIPTION
            "An entry contains a slot4Module's utilization."
    INDEX   { slot4ModuleIndex }
    ::= { slot4ModuleTable 1 }

Slot4ModuleEntry ::=
    SEQUENCE {     
		slot4ModuleIndex                       Integer32,
		slot4ModuleId                           DisplayString,  
		slot4ModuleIfNumber                     Integer32		
    } 

slot4ModuleIndex OBJECT-TYPE
    SYNTAX      Integer32 (1..2147483647)
    MAX-ACCESS  not-accessible
    STATUS      current
    DESCRIPTION
            "A unique value, greater than zero, for each chassis`s slot4."
    ::= { slot4ModuleEntry 1 }

slot4ModuleId OBJECT-TYPE
    SYNTAX      DisplayString (SIZE (0..32))
    MAX-ACCESS  read-only
    STATUS      current
    DESCRIPTION
            "the value of module`s id"
    ::= { slot4ModuleEntry 2 }
  
slot4ModuleIfNumber OBJECT-TYPE
    SYNTAX      Integer32(0..2147483647)
    MAX-ACCESS  read-only
    STATUS      current
    DESCRIPTION
            "The number of network interfaces (regardless of their
            current state) present on this system." 
    ::= { slot4ModuleEntry 3 } 
    
slot4ModuleIfTable OBJECT-TYPE
    SYNTAX      SEQUENCE OF Slot4ModuleIfEntry
    MAX-ACCESS  not-accessible
    STATUS      current
    DESCRIPTION
            "A list of interface entries.  The number of entries is
            given by the value of ifNumber."
    ::= { slot4Module 2 } 
    
slot4ModuleIfEntry OBJECT-TYPE
    SYNTAX      Slot4ModuleIfEntry
    MAX-ACCESS  not-accessible
    STATUS      current
    DESCRIPTION
            "An entry containing management information applicable to a
            particular interface."
    INDEX   { slot4ModuleifIndex }
    ::= { slot4ModuleIfTable 1 }
    
Slot4ModuleIfEntry ::=
    SEQUENCE {
        slot4ModuleifIndex                 InterfaceIndex,  
        slot4ModuleIfId                    DisplayString,  
        slot4ModuleifDescr                 DisplayString,           
        slot4ModuleifType                  IANAifType,   		
        slot4ModuleifMtu                   Integer32,                
        slot4ModuleifSpeed                 Counter64,               
        slot4ModuleifPhysAddress           PhysAddress,              
        slot4ModuleifAdminStatus           INTEGER,                  
        slot4ModuleifOperStatus            INTEGER,                  
        slot4ModuleifLastChange            TimeTicks,                
        slot4ModuleifInOctets              Counter64,                
        slot4ModuleifInUcastPkts           Counter64,                
        slot4ModuleifInNUcastPkts          Counter64,    
        slot4ModuleifInDiscards            Counter64,
        slot4ModuleifInErrors              Counter64,
        slot4ModuleifInFcsErrorPkts        Counter64,
        slot4ModuleifInUnknownProtos       Counter64,	-- deprecated
        slot4ModuleifOutOctets             Counter64,
        slot4ModuleifOutUcastPkts          Counter64,
        slot4ModuleifOutNUcastPkts         Counter64,  -- deprecated
        slot4ModuleifOutDiscards           Counter64,
        slot4ModuleifOutErrors             Counter64,
        slot4ModuleifOutFcsErrorPkts       Counter64,
        slot4ModuleifOutQLen               Gauge32,    -- deprecated  
        slot4ModuleifOutOctetsRate         Counter64,
        slot4ModuleifInOctetsRate          Counter64,
        slot4ModuleifOutPktsRate           Counter64,
        slot4ModuleifInPktsRate            Counter64,
        slot4ModuleifRxPower               DisplayString,
        slot4ModuleifTxPower               DisplayString,
        slot4ModuleifSpecific              OBJECT IDENTIFIER,
        slot4ModuleifTxMirrorList          DisplayString,
        slot4ModuleifRxMirrorList          DisplayString,
        slot4ModuleifRxPowerMin               DisplayString,
        slot4ModuleifRxPowerMax               DisplayString,
        slot4ModuleifTxPowerMin               DisplayString,
        slot4ModuleifTxPowerMax               DisplayString,
        slot4ModuleifRxHisPeak            Counter64,
        slot4ModuleifTxHisPeak            Counter64,
        slot4ModuleifMode                 DisplayString   		
    }         

slot4ModuleifIndex OBJECT-TYPE
    SYNTAX      InterfaceIndex
    MAX-ACCESS  read-only
    STATUS      current
    DESCRIPTION
            "A unique value, greater than zero, for each interface.  It
            is recommended that values are assigned contiguously
            starting from 1.  The value for each interface sub-layer
            must remain constant at least from one re-initialization of
            the entity's network management system to the next re-
            initialization."
    ::= { slot4ModuleIfEntry 1 }
    
slot4ModuleIfId OBJECT-TYPE
    SYNTAX      DisplayString (SIZE (0..32))
    MAX-ACCESS  read-only
    STATUS      current
    DESCRIPTION
            "the value of module`s id"
    ::= { slot4ModuleIfEntry 2 }
    
slot4ModuleifDescr OBJECT-TYPE
    SYNTAX      DisplayString (SIZE (0..255))
    MAX-ACCESS  read-only
    STATUS      current
    DESCRIPTION
            "A textual string containing information about the
            interface.  This string should include the name of the
            manufacturer, the product name and the version of the
            interface hardware/software."
    ::= { slot4ModuleIfEntry 3 }
    
slot4ModuleifType OBJECT-TYPE
    SYNTAX      IANAifType
    MAX-ACCESS  read-only
    STATUS      current
    DESCRIPTION
            "The type of interface.  Additional values for ifType are
            assigned by the Internet Assigned Numbers Authority (IANA),
            through updating the syntax of the IANAifType textual
            convention."
    ::= { slot4ModuleIfEntry 4 }

slot4ModuleifMtu OBJECT-TYPE
    SYNTAX      Integer32(1..2147483647)
    MAX-ACCESS  read-only
    STATUS      current
    DESCRIPTION
            "The size of the largest packet which can be sent/received
            on the interface, specified in octets.  For interfaces that
            are used for transmitting network datagrams, this is the
            size of the largest network datagram that can be sent on the
            interface."
    ::= { slot4ModuleIfEntry 5 }

slot4ModuleifSpeed OBJECT-TYPE
    SYNTAX      Counter64
    MAX-ACCESS  read-only
    STATUS      current
    DESCRIPTION
            "An estimate of the interface's current bandwidth in bits
            per second.  For interfaces which do not vary in bandwidth
            or for those where no accurate estimation can be made, this
            object should contain the nominal bandwidth. For a sub-layer
            which has no concept of bandwidth, this object should be zero."
    ::= { slot4ModuleIfEntry 6 }

slot4ModuleifPhysAddress OBJECT-TYPE
    SYNTAX      PhysAddress
    MAX-ACCESS  read-only
    STATUS      current
    DESCRIPTION
            "The interface's address at its protocol sub-layer.  For
            example, for an 802.x interface, this object normally
            contains a MAC address.  The interface's media-specific MIB
            must define the bit and byte ordering and the format of the
            value of this object.  For interfaces which do not have such
            an address (e.g., a serial line), this object should contain
            an octet string of zero length."
    ::= { slot4ModuleIfEntry 7 }
    
slot4ModuleifAdminStatus OBJECT-TYPE
    SYNTAX  INTEGER {
                up(1),       -- ready to pass packets
                down(2),
                testing(3)   -- in some test mode
            }
    MAX-ACCESS  read-write
    STATUS      current
    DESCRIPTION
            "The desired state of the interface.  The testing(3) state
            indicates that no operational packets can be passed.  When a
            managed system initializes, all interfaces start with
            ifAdminStatus in the down(2) state.  As a result of either
            explicit management action or per configuration information
            retained by the managed system, ifAdminStatus is then
            changed to either the up(1) or testing(3) states (or remains
            in the down(2) state)."
    ::= { slot4ModuleIfEntry 8 }

slot4ModuleifOperStatus OBJECT-TYPE
    SYNTAX  INTEGER {
                up(1),        -- ready to pass packets
                down(2),
                testing(3),   -- in some test mode
                unknown(4),   -- status can not be determined
                              -- for some reason.
                dormant(5),
                notPresent(6),    -- some component is missing
                lowerLayerDown(7) -- down due to state of
                                  -- lower-layer interface(s)
            }
    MAX-ACCESS  read-only
    STATUS      current
    DESCRIPTION
            "The current operational state of the interface.  The
            testing(3) state indicates that no operational packets can
            be passed.  If ifAdminStatus is down(2) then ifOperStatus
            should be down(2).  If ifAdminStatus is changed to up(1)
            then ifOperStatus should change to up(1) if the interface is
            ready to transmit and receive network traffic; it should
            change to dormant(5) if the interface is waiting for
            external actions (such as a serial line waiting for an
            incoming connection); it should remain in the down(2) state
            if and only if there is a fault that prevents it from going
            to the up(1) state; it should remain in the notPresent(6)
            state if the interface has missing (typically, hardware)
            components."
    ::= { slot4ModuleIfEntry 9 }

slot4ModuleifLastChange OBJECT-TYPE
    SYNTAX      TimeTicks
    MAX-ACCESS  read-only
    STATUS      current
    DESCRIPTION
            "The value of sysUpTime at the time the interface entered
            its current operational state.  If the current state was
            entered prior to the last re-initialization of the local
            network management subsystem, then this object contains a
            zero value."
    ::= { slot4ModuleIfEntry 10 }

slot4ModuleifInOctets OBJECT-TYPE
    SYNTAX      Counter64
    MAX-ACCESS  read-only
    STATUS      current
    DESCRIPTION
            "The total number of octets received on the interface,
            including framing characters.

            Discontinuities in the value of this counter can occur at
            re-initialization of the management system, and at other
            times as indicated by the value of
            ifCounterDiscontinuityTime."
    ::= { slot4ModuleIfEntry 11 }

slot4ModuleifInUcastPkts OBJECT-TYPE
    SYNTAX      Counter64
    MAX-ACCESS  read-only
    STATUS      current
    DESCRIPTION
            "The number of packets, delivered by this sub-layer to a
            higher (sub-)layer, which were not addressed to a multicast
            or broadcast address at this sub-layer.

            Discontinuities in the value of this counter can occur at
            re-initialization of the management system, and at other
            times as indicated by the value of
            ifCounterDiscontinuityTime."
    ::= { slot4ModuleIfEntry 12 }

slot4ModuleifInNUcastPkts OBJECT-TYPE
    SYNTAX  Counter64
    MAX-ACCESS  read-only
    STATUS      current
    DESCRIPTION
            "The number of packets, delivered by this sub-layer to a
            higher (sub-)layer, which were addressed to a multicast or
            broadcast address at this sub-layer.

            Discontinuities in the value of this counter can occur at
            re-initialization of the management system, and at other
            times as indicated by the value of
            ifCounterDiscontinuityTime.

            This object is deprecated in favour of ifInMulticastPkts and
            ifInBroadcastPkts."
    ::= { slot4ModuleIfEntry 13 }

slot4ModuleifInDiscards OBJECT-TYPE
    SYNTAX      Counter64
    MAX-ACCESS  read-only
    STATUS      current
    DESCRIPTION
            "The number of inbound packets which were chosen to be
            discarded even though no errors had been detected to prevent

            their being deliverable to a higher-layer protocol.  One
            possible reason for discarding such a packet could be to
            free up buffer space.

            Discontinuities in the value of this counter can occur at
            re-initialization of the management system, and at other
            times as indicated by the value of
            ifCounterDiscontinuityTime."
    ::= { slot4ModuleIfEntry 14 }

slot4ModuleifInErrors OBJECT-TYPE
    SYNTAX      Counter64
    MAX-ACCESS  read-only
    STATUS      current
    DESCRIPTION
            "For packet-oriented interfaces, the number of inbound
            packets that contained errors preventing them from being
            deliverable to a higher-layer protocol.  For character-
            oriented or fixed-length interfaces, the number of inbound
            transmission units that contained errors preventing them
            from being deliverable to a higher-layer protocol.

            Discontinuities in the value of this counter can occur at
            re-initialization of the management system, and at other
            times as indicated by the value of
            ifCounterDiscontinuityTime."
    ::= { slot4ModuleIfEntry 15 }

slot4ModuleifInFcsErrorPkts OBJECT-TYPE
    SYNTAX      Counter64
    MAX-ACCESS  read-only
    STATUS      current
    DESCRIPTION
            "FCS error pakets."
    ::= { slot4ModuleIfEntry 16 }

slot4ModuleifInUnknownProtos OBJECT-TYPE
    SYNTAX      Counter64
    MAX-ACCESS  read-only
    STATUS      current
    DESCRIPTION
            "For packet-oriented interfaces, the number of packets
            received via the interface which were discarded because of
            an unknown or unsupported protocol.  For character-oriented
            or fixed-length interfaces that support protocol
            multiplexing the number of transmission units received via
            the interface which were discarded because of an unknown or
            unsupported protocol.  For any interface that does not
            support protocol multiplexing, this counter will always be
            0.

            Discontinuities in the value of this counter can occur at
            re-initialization of the management system, and at other
            times as indicated by the value of
            ifCounterDiscontinuityTime."
    ::= { slot4ModuleIfEntry 17 }

slot4ModuleifOutOctets OBJECT-TYPE
    SYNTAX      Counter64
    MAX-ACCESS  read-only
    STATUS      current
    DESCRIPTION
            "The total number of octets transmitted out of the
            interface, including framing characters.

            Discontinuities in the value of this counter can occur at
            re-initialization of the management system, and at other
            times as indicated by the value of
            ifCounterDiscontinuityTime."
    ::= { slot4ModuleIfEntry 18 }

slot4ModuleifOutUcastPkts OBJECT-TYPE
    SYNTAX      Counter64
    MAX-ACCESS  read-only
    STATUS      current
    DESCRIPTION
            "The total number of packets that higher-level protocols
            requested be transmitted, and which were not addressed to a
            multicast or broadcast address at this sub-layer, including
            those that were discarded or not sent.

            Discontinuities in the value of this counter can occur at
            re-initialization of the management system, and at other
            times as indicated by the value of
            ifCounterDiscontinuityTime."
    ::= { slot4ModuleIfEntry 19 }

slot4ModuleifOutNUcastPkts OBJECT-TYPE
    SYNTAX      Counter64
    MAX-ACCESS  read-only
    STATUS      deprecated
    DESCRIPTION
            "The total number of packets that higher-level protocols
            requested be transmitted, and which were addressed to a
            multicast or broadcast address at this sub-layer, including
            those that were discarded or not sent.

            Discontinuities in the value of this counter can occur at
            re-initialization of the management system, and at other
            times as indicated by the value of
            ifCounterDiscontinuityTime.

            This object is deprecated in favour of ifOutMulticastPkts
            and ifOutBroadcastPkts."
    ::= { slot4ModuleIfEntry 20 }

slot4ModuleifOutDiscards OBJECT-TYPE
    SYNTAX      Counter64
    MAX-ACCESS  read-only
    STATUS      current
    DESCRIPTION
            "The number of outbound packets which were chosen to be
            discarded even though no errors had been detected to prevent
            their being transmitted.  One possible reason for discarding
            such a packet could be to free up buffer space.

            Discontinuities in the value of this counter can occur at
            re-initialization of the management system, and at other
            times as indicated by the value of
            ifCounterDiscontinuityTime."
    ::= { slot4ModuleIfEntry 21 }

slot4ModuleifOutErrors OBJECT-TYPE
    SYNTAX      Counter64
    MAX-ACCESS  read-only
    STATUS      current
    DESCRIPTION
            "For packet-oriented interfaces, the number of outbound
            packets that could not be transmitted because of errors.
            For character-oriented or fixed-length interfaces, the
            number of outbound transmission units that could not be
            transmitted because of errors.

            Discontinuities in the value of this counter can occur at
            re-initialization of the management system, and at other
            times as indicated by the value of
            ifCounterDiscontinuityTime."
    ::= { slot4ModuleIfEntry 22 }

slot4ModuleifOutFcsErrorPkts OBJECT-TYPE
    SYNTAX      Counter64
    MAX-ACCESS  read-only
    STATUS      current
    DESCRIPTION
            "FCS error pakets."
    ::= { slot4ModuleIfEntry 23 }

slot4ModuleifOutQLen OBJECT-TYPE
    SYNTAX      Gauge32
    MAX-ACCESS  read-only
    STATUS      deprecated
    DESCRIPTION
            "The length of the output packet queue (in packets)."
    ::= { slot4ModuleIfEntry 24 }

slot4ModuleifOutOctetsRate OBJECT-TYPE
    SYNTAX      Counter64
    MAX-ACCESS  read-only
    STATUS      current
    DESCRIPTION
            "The speed of octets trans on the interface(kbps)"
    ::= { slot4ModuleIfEntry 25 }

slot4ModuleifInOctetsRate OBJECT-TYPE
    SYNTAX      Counter64
    MAX-ACCESS  read-only
    STATUS      current
    DESCRIPTION
            "The speed of octets received on the interface(kbps)"
    ::= { slot4ModuleIfEntry 26 }

slot4ModuleifOutPktsRate OBJECT-TYPE
    SYNTAX      Counter64
    MAX-ACCESS  read-only
    STATUS      current
    DESCRIPTION
            "The speed of packets trans on the interface(pps)"
    ::= { slot4ModuleIfEntry 27 }

slot4ModuleifInPktsRate OBJECT-TYPE
    SYNTAX      Counter64
    MAX-ACCESS  read-only
    STATUS      current
    DESCRIPTION
            "The speed of octets received on the interface(kbps)"
    ::= { slot4ModuleIfEntry 28 }

slot4ModuleifRxPower OBJECT-TYPE
    SYNTAX      DisplayString (SIZE (0..255))
    MAX-ACCESS  read-only
    STATUS      current
    DESCRIPTION
            "the value of interface's received power, in dbm format."
    ::= { slot4ModuleIfEntry 29 }

slot4ModuleifTxPower OBJECT-TYPE
    SYNTAX      DisplayString (SIZE (0..255))
    MAX-ACCESS  read-only
    STATUS      current
    DESCRIPTION
            "the value of interface's send power, in dbm format."
    ::= { slot4ModuleIfEntry 30 }

slot4ModuleifSpecific OBJECT-TYPE
    SYNTAX      OBJECT IDENTIFIER
    MAX-ACCESS  read-only
    STATUS      deprecated
    DESCRIPTION
            "A reference to MIB definitions specific to the particular
            media being used to realize the interface.  It is

            recommended that this value point to an instance of a MIB
            object in the media-specific MIB, i.e., that this object
            have the semantics associated with the InstancePointer
            textual convention defined in RFC 2579.  In fact, it is
            recommended that the media-specific MIB specify what value
            ifSpecific should/can take for values of ifType.  If no MIB
            definitions specific to the particular media are available,
            the value should be set to the OBJECT IDENTIFIER { 0 0 }."
    ::= { slot4ModuleIfEntry 31 }  
  
slot4ModuleifTxMirrorList OBJECT-TYPE
    SYNTAX      DisplayString (SIZE (0..255))
    MAX-ACCESS  read-only
    STATUS      deprecated
    DESCRIPTION
            "the interface tx mirror list."
    ::= { slot4ModuleIfEntry 32 }  
 
slot4ModuleifRxMirrorList OBJECT-TYPE
    SYNTAX      DisplayString (SIZE (0..255))
    MAX-ACCESS  read-only
    STATUS      deprecated
    DESCRIPTION
            "the interface rx mirror list."
    ::= { slot4ModuleIfEntry 33 }  

slot4ModuleifRxPowerMin OBJECT-TYPE
    SYNTAX      DisplayString (SIZE (0..255))
    MAX-ACCESS  read-only
    STATUS      deprecated
    DESCRIPTION
            "the interface min rx power."
    ::= { slot4ModuleIfEntry 34 }  

slot4ModuleifRxPowerMax OBJECT-TYPE
    SYNTAX      DisplayString (SIZE (0..255))
    MAX-ACCESS  read-only
    STATUS      deprecated
    DESCRIPTION
            "the interface max rx power."
    ::= { slot4ModuleIfEntry 35 }  

slot4ModuleifTxPowerMin OBJECT-TYPE
    SYNTAX      DisplayString (SIZE (0..255))
    MAX-ACCESS  read-only
    STATUS      deprecated
    DESCRIPTION
            "the interface min tx power."
    ::= { slot4ModuleIfEntry 36 }  

slot4ModuleifTxPowerMax OBJECT-TYPE
    SYNTAX      DisplayString (SIZE (0..255))
    MAX-ACCESS  read-only
    STATUS      deprecated
    DESCRIPTION
            "the interface max tx power."
    ::= { slot4ModuleIfEntry 37 }  

slot4ModuleifRxHisPeak OBJECT-TYPE
    SYNTAX      Counter64
    MAX-ACCESS  read-only
    STATUS      current
    DESCRIPTION
            "The max speed of rx rate on the interface(kbps)"
    ::= { slot4ModuleIfEntry 38 }

slot4ModuleifTxHisPeak OBJECT-TYPE
    SYNTAX      Counter64
    MAX-ACCESS  read-only
    STATUS      current
    DESCRIPTION
            "The max speed of tx rate on the interface(kbps)"
    ::= { slot4ModuleIfEntry 39 }

slot4ModuleifMode OBJECT-TYPE
    SYNTAX      DisplayString (SIZE (0..255))
    MAX-ACCESS  read-only
    STATUS      deprecated
    DESCRIPTION
            "the interface if mode."
    ::= { slot4ModuleIfEntry 40 }  

-- slot 5 --

-- slot5Table --

slot5Table OBJECT-TYPE
    SYNTAX      SEQUENCE OF Slot5Entry
    MAX-ACCESS  not-accessible
    STATUS      current
    DESCRIPTION
            "A list of all slot5Type's utilization."
    ::= { slot5 1 }  

slot5Entry OBJECT-TYPE
    SYNTAX      Slot5Entry
    MAX-ACCESS  not-accessible
    STATUS      current
    DESCRIPTION
            "An entry contains a slot5's utilization."
    INDEX   { slot5Index }
    ::= { slot5Table 1 }

Slot5Entry ::=
    SEQUENCE {     
		slot5Index                       Integer32,
		slot5Type                        DisplayString,
		slot5Status                      DisplayString,		
        slot5SerialNumber                DisplayString,		
        slot5Temperature                 DisplayString
    }  

slot5Index OBJECT-TYPE
    SYNTAX      Integer32 (1..2147483647)
    MAX-ACCESS  not-accessible
    STATUS      current
    DESCRIPTION
            "A unique value, greater than zero, for each chassis`s slot5."
    ::= { slot5Entry 1 }

slot5Type OBJECT-TYPE
    SYNTAX      DisplayString (SIZE (0..255))
    MAX-ACCESS  read-only
    STATUS      current
    DESCRIPTION
            "the slot5Type of each chassis."
    ::= { slot5Entry 2 }

slot5Status OBJECT-TYPE
    SYNTAX      DisplayString (SIZE (0..255))
    MAX-ACCESS  read-only
    STATUS      current
    DESCRIPTION
            "A string to describe the board status." 
    ::= { slot5Entry 3 }   


slot5SerialNumber OBJECT-TYPE
    SYNTAX      DisplayString (SIZE (0..255))
    MAX-ACCESS  read-only
    STATUS      current
    DESCRIPTION
            "A string to describe the board serial number." 
    ::= { slot5Entry 4 }   

slot5Temperature OBJECT-TYPE
    SYNTAX      DisplayString (SIZE (0..255))
    MAX-ACCESS  read-only
    STATUS      current
    DESCRIPTION
            "A string to describe the board temperature." 
    ::= { slot5Entry 5 }   


slot5Module OBJECT IDENTIFIER ::= { slot5 2 }

-- slot5ModuleTable --
slot5ModuleTable OBJECT-TYPE
    SYNTAX      SEQUENCE OF Slot5ModuleEntry
    MAX-ACCESS  not-accessible
    STATUS      current
    DESCRIPTION
            "A list of all slot5Module's utilization."
    ::= { slot5Module 1 }  

slot5ModuleEntry OBJECT-TYPE
    SYNTAX      Slot5ModuleEntry
    MAX-ACCESS  not-accessible
    STATUS      current
    DESCRIPTION
            "An entry contains a slot5Module's utilization."
    INDEX   { slot5ModuleIndex }
    ::= { slot5ModuleTable 1 }

Slot5ModuleEntry ::=
    SEQUENCE {     
		slot5ModuleIndex                       Integer32,
		slot5ModuleId                           DisplayString,  
		slot5ModuleIfNumber                     Integer32		
    } 

slot5ModuleIndex OBJECT-TYPE
    SYNTAX      Integer32 (1..2147483647)
    MAX-ACCESS  not-accessible
    STATUS      current
    DESCRIPTION
            "A unique value, greater than zero, for each chassis`s slot5."
    ::= { slot5ModuleEntry 1 }

slot5ModuleId OBJECT-TYPE
    SYNTAX      DisplayString (SIZE (0..32))
    MAX-ACCESS  read-only
    STATUS      current
    DESCRIPTION
            "the value of module`s id"
    ::= { slot5ModuleEntry 2 }
  
slot5ModuleIfNumber OBJECT-TYPE
    SYNTAX      Integer32(0..2147483647)
    MAX-ACCESS  read-only
    STATUS      current
    DESCRIPTION
            "The number of network interfaces (regardless of their
            current state) present on this system." 
    ::= { slot5ModuleEntry 3 } 
    
slot5ModuleIfTable OBJECT-TYPE
    SYNTAX      SEQUENCE OF Slot5ModuleIfEntry
    MAX-ACCESS  not-accessible
    STATUS      current
    DESCRIPTION
            "A list of interface entries.  The number of entries is
            given by the value of ifNumber."
    ::= { slot5Module 2 } 
    
slot5ModuleIfEntry OBJECT-TYPE
    SYNTAX      Slot5ModuleIfEntry
    MAX-ACCESS  not-accessible
    STATUS      current
    DESCRIPTION
            "An entry containing management information applicable to a
            particular interface."
    INDEX   { slot5ModuleifIndex }
    ::= { slot5ModuleIfTable 1 }
    
Slot5ModuleIfEntry ::=
    SEQUENCE {
        slot5ModuleifIndex                 InterfaceIndex,  
        slot5ModuleIfId                    DisplayString,  
        slot5ModuleifDescr                 DisplayString,           
        slot5ModuleifType                  IANAifType,   		
        slot5ModuleifMtu                   Integer32,                
        slot5ModuleifSpeed                 Counter64,               
        slot5ModuleifPhysAddress           PhysAddress,              
        slot5ModuleifAdminStatus           INTEGER,                  
        slot5ModuleifOperStatus            INTEGER,                  
        slot5ModuleifLastChange            TimeTicks,                
        slot5ModuleifInOctets              Counter64,                
        slot5ModuleifInUcastPkts           Counter64,                
        slot5ModuleifInNUcastPkts          Counter64,  
        slot5ModuleifInDiscards            Counter64,
        slot5ModuleifInErrors              Counter64,
        slot5ModuleifInFcsErrorPkts        Counter64,
        slot5ModuleifInUnknownProtos       Counter64,	-- deprecated
        slot5ModuleifOutOctets             Counter64,
        slot5ModuleifOutUcastPkts          Counter64,
        slot5ModuleifOutNUcastPkts         Counter64,  -- deprecated
        slot5ModuleifOutDiscards           Counter64,
        slot5ModuleifOutErrors             Counter64,
        slot5ModuleifOutFcsErrorPkts       Counter64,
        slot5ModuleifOutQLen               Gauge32,    -- deprecated  
        slot5ModuleifOutOctetsRate         Counter64,
        slot5ModuleifInOctetsRate          Counter64,
        slot5ModuleifOutPktsRate           Counter64,
        slot5ModuleifInPktsRate            Counter64,
        slot5ModuleifRxPower               DisplayString,
        slot5ModuleifTxPower               DisplayString,
        slot5ModuleifSpecific              OBJECT IDENTIFIER,
        slot5ModuleifTxMirrorList          DisplayString,
        slot5ModuleifRxMirrorList          DisplayString,
        slot5ModuleifRxPowerMin               DisplayString,
        slot5ModuleifRxPowerMax               DisplayString,
        slot5ModuleifTxPowerMin               DisplayString,
        slot5ModuleifTxPowerMax               DisplayString,
        slot5ModuleifRxHisPeak            Counter64,
        slot5ModuleifTxHisPeak            Counter64,
        slot5ModuleifMode                 DisplayString   		
    }         

slot5ModuleifIndex OBJECT-TYPE
    SYNTAX      InterfaceIndex
    MAX-ACCESS  read-only
    STATUS      current
    DESCRIPTION
            "A unique value, greater than zero, for each interface.  It
            is recommended that values are assigned contiguously
            starting from 1.  The value for each interface sub-layer
            must remain constant at least from one re-initialization of
            the entity's network management system to the next re-
            initialization."
    ::= { slot5ModuleIfEntry 1 }
    
slot5ModuleIfId OBJECT-TYPE
    SYNTAX      DisplayString (SIZE (0..32))
    MAX-ACCESS  read-only
    STATUS      current
    DESCRIPTION
            "the value of module`s id"
    ::= { slot5ModuleIfEntry 2 }
    
slot5ModuleifDescr OBJECT-TYPE
    SYNTAX      DisplayString (SIZE (0..255))
    MAX-ACCESS  read-only
    STATUS      current
    DESCRIPTION
            "A textual string containing information about the
            interface.  This string should include the name of the
            manufacturer, the product name and the version of the
            interface hardware/software."
    ::= { slot5ModuleIfEntry 3 }
    
slot5ModuleifType OBJECT-TYPE
    SYNTAX      IANAifType
    MAX-ACCESS  read-only
    STATUS      current
    DESCRIPTION
            "The type of interface.  Additional values for ifType are
            assigned by the Internet Assigned Numbers Authority (IANA),
            through updating the syntax of the IANAifType textual
            convention."
    ::= { slot5ModuleIfEntry 4 }

slot5ModuleifMtu OBJECT-TYPE
    SYNTAX      Integer32(1..2147483647)
    MAX-ACCESS  read-only
    STATUS      current
    DESCRIPTION
            "The size of the largest packet which can be sent/received
            on the interface, specified in octets.  For interfaces that
            are used for transmitting network datagrams, this is the
            size of the largest network datagram that can be sent on the
            interface."
    ::= { slot5ModuleIfEntry 5 }

slot5ModuleifSpeed OBJECT-TYPE
    SYNTAX      Counter64
    MAX-ACCESS  read-only
    STATUS      current
    DESCRIPTION
            "An estimate of the interface's current bandwidth in bits
            per second.  For interfaces which do not vary in bandwidth
            or for those where no accurate estimation can be made, this
            object should contain the nominal bandwidth. For a sub-layer
            which has no concept of bandwidth, this object should be zero."
    ::= { slot5ModuleIfEntry 6 }

slot5ModuleifPhysAddress OBJECT-TYPE
    SYNTAX      PhysAddress
    MAX-ACCESS  read-only
    STATUS      current
    DESCRIPTION
            "The interface's address at its protocol sub-layer.  For
            example, for an 802.x interface, this object normally
            contains a MAC address.  The interface's media-specific MIB
            must define the bit and byte ordering and the format of the
            value of this object.  For interfaces which do not have such
            an address (e.g., a serial line), this object should contain
            an octet string of zero length."
    ::= { slot5ModuleIfEntry 7 }
    
slot5ModuleifAdminStatus OBJECT-TYPE
    SYNTAX  INTEGER {
                up(1),       -- ready to pass packets
                down(2),
                testing(3)   -- in some test mode
            }
    MAX-ACCESS  read-write
    STATUS      current
    DESCRIPTION
            "The desired state of the interface.  The testing(3) state
            indicates that no operational packets can be passed.  When a
            managed system initializes, all interfaces start with
            ifAdminStatus in the down(2) state.  As a result of either
            explicit management action or per configuration information
            retained by the managed system, ifAdminStatus is then
            changed to either the up(1) or testing(3) states (or remains
            in the down(2) state)."
    ::= { slot5ModuleIfEntry 8 }

slot5ModuleifOperStatus OBJECT-TYPE
    SYNTAX  INTEGER {
                up(1),        -- ready to pass packets
                down(2),
                testing(3),   -- in some test mode
                unknown(4),   -- status can not be determined
                              -- for some reason.
                dormant(5),
                notPresent(6),    -- some component is missing
                lowerLayerDown(7) -- down due to state of
                                  -- lower-layer interface(s)
            }
    MAX-ACCESS  read-only
    STATUS      current
    DESCRIPTION
            "The current operational state of the interface.  The
            testing(3) state indicates that no operational packets can
            be passed.  If ifAdminStatus is down(2) then ifOperStatus
            should be down(2).  If ifAdminStatus is changed to up(1)
            then ifOperStatus should change to up(1) if the interface is
            ready to transmit and receive network traffic; it should
            change to dormant(5) if the interface is waiting for
            external actions (such as a serial line waiting for an
            incoming connection); it should remain in the down(2) state
            if and only if there is a fault that prevents it from going
            to the up(1) state; it should remain in the notPresent(6)
            state if the interface has missing (typically, hardware)
            components."
    ::= { slot5ModuleIfEntry 9 }

slot5ModuleifLastChange OBJECT-TYPE
    SYNTAX      TimeTicks
    MAX-ACCESS  read-only
    STATUS      current
    DESCRIPTION
            "The value of sysUpTime at the time the interface entered
            its current operational state.  If the current state was
            entered prior to the last re-initialization of the local
            network management subsystem, then this object contains a
            zero value."
    ::= { slot5ModuleIfEntry 10 }

slot5ModuleifInOctets OBJECT-TYPE
    SYNTAX      Counter64
    MAX-ACCESS  read-only
    STATUS      current
    DESCRIPTION
            "The total number of octets received on the interface,
            including framing characters.

            Discontinuities in the value of this counter can occur at
            re-initialization of the management system, and at other
            times as indicated by the value of
            ifCounterDiscontinuityTime."
    ::= { slot5ModuleIfEntry 11 }

slot5ModuleifInUcastPkts OBJECT-TYPE
    SYNTAX      Counter64
    MAX-ACCESS  read-only
    STATUS      current
    DESCRIPTION
            "The number of packets, delivered by this sub-layer to a
            higher (sub-)layer, which were not addressed to a multicast
            or broadcast address at this sub-layer.

            Discontinuities in the value of this counter can occur at
            re-initialization of the management system, and at other
            times as indicated by the value of
            ifCounterDiscontinuityTime."
    ::= { slot5ModuleIfEntry 12 }

slot5ModuleifInNUcastPkts OBJECT-TYPE
    SYNTAX  Counter64
    MAX-ACCESS  read-only
    STATUS      current
    DESCRIPTION
            "The number of packets, delivered by this sub-layer to a
            higher (sub-)layer, which were addressed to a multicast or
            broadcast address at this sub-layer.

            Discontinuities in the value of this counter can occur at
            re-initialization of the management system, and at other
            times as indicated by the value of
            ifCounterDiscontinuityTime.

            This object is deprecated in favour of ifInMulticastPkts and
            ifInBroadcastPkts."
    ::= { slot5ModuleIfEntry 13 }

slot5ModuleifInDiscards OBJECT-TYPE
    SYNTAX      Counter64
    MAX-ACCESS  read-only
    STATUS      current
    DESCRIPTION
            "The number of inbound packets which were chosen to be
            discarded even though no errors had been detected to prevent

            their being deliverable to a higher-layer protocol.  One
            possible reason for discarding such a packet could be to
            free up buffer space.

            Discontinuities in the value of this counter can occur at
            re-initialization of the management system, and at other
            times as indicated by the value of
            ifCounterDiscontinuityTime."
    ::= { slot5ModuleIfEntry 14 }

slot5ModuleifInErrors OBJECT-TYPE
    SYNTAX      Counter64
    MAX-ACCESS  read-only
    STATUS      current
    DESCRIPTION
            "For packet-oriented interfaces, the number of inbound
            packets that contained errors preventing them from being
            deliverable to a higher-layer protocol.  For character-
            oriented or fixed-length interfaces, the number of inbound
            transmission units that contained errors preventing them
            from being deliverable to a higher-layer protocol.

            Discontinuities in the value of this counter can occur at
            re-initialization of the management system, and at other
            times as indicated by the value of
            ifCounterDiscontinuityTime."
    ::= { slot5ModuleIfEntry 15 }

slot5ModuleifInFcsErrorPkts OBJECT-TYPE
    SYNTAX      Counter64
    MAX-ACCESS  read-only
    STATUS      current
    DESCRIPTION
            "FCS error pakets."
    ::= { slot5ModuleIfEntry 16 }

slot5ModuleifInUnknownProtos OBJECT-TYPE
    SYNTAX      Counter64
    MAX-ACCESS  read-only
    STATUS      current
    DESCRIPTION
            "For packet-oriented interfaces, the number of packets
            received via the interface which were discarded because of
            an unknown or unsupported protocol.  For character-oriented
            or fixed-length interfaces that support protocol
            multiplexing the number of transmission units received via
            the interface which were discarded because of an unknown or
            unsupported protocol.  For any interface that does not
            support protocol multiplexing, this counter will always be
            0.

            Discontinuities in the value of this counter can occur at
            re-initialization of the management system, and at other
            times as indicated by the value of
            ifCounterDiscontinuityTime."
    ::= { slot5ModuleIfEntry 17 }

slot5ModuleifOutOctets OBJECT-TYPE
    SYNTAX      Counter64
    MAX-ACCESS  read-only
    STATUS      current
    DESCRIPTION
            "The total number of octets transmitted out of the
            interface, including framing characters.

            Discontinuities in the value of this counter can occur at
            re-initialization of the management system, and at other
            times as indicated by the value of
            ifCounterDiscontinuityTime."
    ::= { slot5ModuleIfEntry 18 }

slot5ModuleifOutUcastPkts OBJECT-TYPE
    SYNTAX      Counter64
    MAX-ACCESS  read-only
    STATUS      current
    DESCRIPTION
            "The total number of packets that higher-level protocols
            requested be transmitted, and which were not addressed to a
            multicast or broadcast address at this sub-layer, including
            those that were discarded or not sent.

            Discontinuities in the value of this counter can occur at
            re-initialization of the management system, and at other
            times as indicated by the value of
            ifCounterDiscontinuityTime."
    ::= { slot5ModuleIfEntry 19 }

slot5ModuleifOutNUcastPkts OBJECT-TYPE
    SYNTAX      Counter64
    MAX-ACCESS  read-only
    STATUS      deprecated
    DESCRIPTION
            "The total number of packets that higher-level protocols
            requested be transmitted, and which were addressed to a
            multicast or broadcast address at this sub-layer, including
            those that were discarded or not sent.

            Discontinuities in the value of this counter can occur at
            re-initialization of the management system, and at other
            times as indicated by the value of
            ifCounterDiscontinuityTime.

            This object is deprecated in favour of ifOutMulticastPkts
            and ifOutBroadcastPkts."
    ::= { slot5ModuleIfEntry 20 }

slot5ModuleifOutDiscards OBJECT-TYPE
    SYNTAX      Counter64
    MAX-ACCESS  read-only
    STATUS      current
    DESCRIPTION
            "The number of outbound packets which were chosen to be
            discarded even though no errors had been detected to prevent
            their being transmitted.  One possible reason for discarding
            such a packet could be to free up buffer space.

            Discontinuities in the value of this counter can occur at
            re-initialization of the management system, and at other
            times as indicated by the value of
            ifCounterDiscontinuityTime."
    ::= { slot5ModuleIfEntry 21 }

slot5ModuleifOutErrors OBJECT-TYPE
    SYNTAX      Counter64
    MAX-ACCESS  read-only
    STATUS      current
    DESCRIPTION
            "For packet-oriented interfaces, the number of outbound
            packets that could not be transmitted because of errors.
            For character-oriented or fixed-length interfaces, the
            number of outbound transmission units that could not be
            transmitted because of errors.

            Discontinuities in the value of this counter can occur at
            re-initialization of the management system, and at other
            times as indicated by the value of
            ifCounterDiscontinuityTime."
    ::= { slot5ModuleIfEntry 22 }

slot5ModuleifOutFcsErrorPkts OBJECT-TYPE
    SYNTAX      Counter64
    MAX-ACCESS  read-only
    STATUS      current
    DESCRIPTION
            "FCS error pakets."
    ::= { slot5ModuleIfEntry 23 }

slot5ModuleifOutQLen OBJECT-TYPE
    SYNTAX      Gauge32
    MAX-ACCESS  read-only
    STATUS      deprecated
    DESCRIPTION
            "The length of the output packet queue (in packets)."
    ::= { slot5ModuleIfEntry 24 }

slot5ModuleifOutOctetsRate OBJECT-TYPE
    SYNTAX      Counter64
    MAX-ACCESS  read-only
    STATUS      current
    DESCRIPTION
            "The speed of octets trans on the interface(kbps)"
    ::= { slot5ModuleIfEntry 25 }

slot5ModuleifInOctetsRate OBJECT-TYPE
    SYNTAX      Counter64
    MAX-ACCESS  read-only
    STATUS      current
    DESCRIPTION
            "The speed of octets received on the interface(kbps)"
    ::= { slot5ModuleIfEntry 26 }

slot5ModuleifOutPktsRate OBJECT-TYPE
    SYNTAX      Counter64
    MAX-ACCESS  read-only
    STATUS      current
    DESCRIPTION
            "The speed of packets trans on the interface(pps)"
    ::= { slot5ModuleIfEntry 27 }

slot5ModuleifInPktsRate OBJECT-TYPE
    SYNTAX      Counter64
    MAX-ACCESS  read-only
    STATUS      current
    DESCRIPTION
            "The speed of octets received on the interface(kbps)"
    ::= { slot5ModuleIfEntry 28 }

slot5ModuleifRxPower OBJECT-TYPE
    SYNTAX      DisplayString (SIZE (0..255))
    MAX-ACCESS  read-only
    STATUS      current
    DESCRIPTION
            "the value of interface's received power, in dbm format."
    ::= { slot5ModuleIfEntry 29 }

slot5ModuleifTxPower OBJECT-TYPE
    SYNTAX      DisplayString (SIZE (0..255))
    MAX-ACCESS  read-only
    STATUS      current
    DESCRIPTION
            "the value of interface's send power, in dbm format."
    ::= { slot5ModuleIfEntry 30 }

slot5ModuleifSpecific OBJECT-TYPE
    SYNTAX      OBJECT IDENTIFIER
    MAX-ACCESS  read-only
    STATUS      deprecated
    DESCRIPTION
            "A reference to MIB definitions specific to the particular
            media being used to realize the interface.  It is

            recommended that this value point to an instance of a MIB
            object in the media-specific MIB, i.e., that this object
            have the semantics associated with the InstancePointer
            textual convention defined in RFC 2579.  In fact, it is
            recommended that the media-specific MIB specify what value
            ifSpecific should/can take for values of ifType.  If no MIB
            definitions specific to the particular media are available,
            the value should be set to the OBJECT IDENTIFIER { 0 0 }."
    ::= { slot5ModuleIfEntry 31 }  
  
slot5ModuleifTxMirrorList OBJECT-TYPE
    SYNTAX      DisplayString (SIZE (0..255))
    MAX-ACCESS  read-only
    STATUS      deprecated
    DESCRIPTION
            "the interface tx mirror list."
    ::= { slot5ModuleIfEntry 32 }  
 
slot5ModuleifRxMirrorList OBJECT-TYPE
    SYNTAX      DisplayString (SIZE (0..255))
    MAX-ACCESS  read-only
    STATUS      deprecated
    DESCRIPTION
            "the interface rx mirror list."
    ::= { slot5ModuleIfEntry 33 }  

slot5ModuleifRxPowerMin OBJECT-TYPE
    SYNTAX      DisplayString (SIZE (0..255))
    MAX-ACCESS  read-only
    STATUS      deprecated
    DESCRIPTION
            "the interface min rx power."
    ::= { slot5ModuleIfEntry 34 }  

slot5ModuleifRxPowerMax OBJECT-TYPE
    SYNTAX      DisplayString (SIZE (0..255))
    MAX-ACCESS  read-only
    STATUS      deprecated
    DESCRIPTION
            "the interface max rx power."
    ::= { slot5ModuleIfEntry 35 }  

slot5ModuleifTxPowerMin OBJECT-TYPE
    SYNTAX      DisplayString (SIZE (0..255))
    MAX-ACCESS  read-only
    STATUS      deprecated
    DESCRIPTION
            "the interface min tx power."
    ::= { slot5ModuleIfEntry 36 }  

slot5ModuleifTxPowerMax OBJECT-TYPE
    SYNTAX      DisplayString (SIZE (0..255))
    MAX-ACCESS  read-only
    STATUS      deprecated
    DESCRIPTION
            "the interface max tx power."
    ::= { slot5ModuleIfEntry 37 }  

slot5ModuleifRxHisPeak OBJECT-TYPE
    SYNTAX      Counter64
    MAX-ACCESS  read-only
    STATUS      current
    DESCRIPTION
            "The max speed of rx rate on the interface(kbps)"
    ::= { slot5ModuleIfEntry 38 }

slot5ModuleifTxHisPeak OBJECT-TYPE
    SYNTAX      Counter64
    MAX-ACCESS  read-only
    STATUS      current
    DESCRIPTION
            "The max speed of tx rate on the interface(kbps)"
    ::= { slot5ModuleIfEntry 39 }

slot5ModuleifMode OBJECT-TYPE
    SYNTAX      DisplayString (SIZE (0..255))
    MAX-ACCESS  read-only
    STATUS      deprecated
    DESCRIPTION
            "the interface if mode."
    ::= { slot5ModuleIfEntry 40 }  

-- slot 6 --

-- slot6Table --

slot6Table OBJECT-TYPE
    SYNTAX      SEQUENCE OF Slot6Entry
    MAX-ACCESS  not-accessible
    STATUS      current
    DESCRIPTION
            "A list of all slot6Type's utilization."
    ::= { slot6 1 }  

slot6Entry OBJECT-TYPE
    SYNTAX      Slot6Entry
    MAX-ACCESS  not-accessible
    STATUS      current
    DESCRIPTION
            "An entry contains a slot6's utilization."
    INDEX   { slot6Index }
    ::= { slot6Table 1 }

Slot6Entry ::=
    SEQUENCE {     
		slot6Index                       Integer32,
		slot6Type                        DisplayString,
		slot6Status                      DisplayString,		
        slot6SerialNumber                DisplayString,		
        slot6Temperature                 DisplayString
    }  

slot6Index OBJECT-TYPE
    SYNTAX      Integer32 (1..2147483647)
    MAX-ACCESS  not-accessible
    STATUS      current
    DESCRIPTION
            "A unique value, greater than zero, for each chassis`s slot6."
    ::= { slot6Entry 1 }

slot6Type OBJECT-TYPE
    SYNTAX      DisplayString (SIZE (0..255))
    MAX-ACCESS  read-only
    STATUS      current
    DESCRIPTION
            "the slot6Type of each chassis."
    ::= { slot6Entry 2 }

slot6Status OBJECT-TYPE
    SYNTAX      DisplayString (SIZE (0..255))
    MAX-ACCESS  read-only
    STATUS      current
    DESCRIPTION
            "A string to describe the board status." 
    ::= { slot6Entry 3 }   


slot6SerialNumber OBJECT-TYPE
    SYNTAX      DisplayString (SIZE (0..255))
    MAX-ACCESS  read-only
    STATUS      current
    DESCRIPTION
            "A string to describe the board serial number." 
    ::= { slot6Entry 4 }   

slot6Temperature OBJECT-TYPE
    SYNTAX      DisplayString (SIZE (0..255))
    MAX-ACCESS  read-only
    STATUS      current
    DESCRIPTION
            "A string to describe the board temperature." 
    ::= { slot6Entry 5 }   


slot6Module OBJECT IDENTIFIER ::= { slot6 2 }

-- slot6ModuleTable --
slot6ModuleTable OBJECT-TYPE
    SYNTAX      SEQUENCE OF Slot6ModuleEntry
    MAX-ACCESS  not-accessible
    STATUS      current
    DESCRIPTION
            "A list of all slot6Module's utilization."
    ::= { slot6Module 1 }  

slot6ModuleEntry OBJECT-TYPE
    SYNTAX      Slot6ModuleEntry
    MAX-ACCESS  not-accessible
    STATUS      current
    DESCRIPTION
            "An entry contains a slot6Module's utilization."
    INDEX   { slot6ModuleIndex }
    ::= { slot6ModuleTable 1 }

Slot6ModuleEntry ::=
    SEQUENCE {     
		slot6ModuleIndex                       Integer32,
		slot6ModuleId                           DisplayString,  
		slot6ModuleIfNumber                     Integer32		
    } 

slot6ModuleIndex OBJECT-TYPE
    SYNTAX      Integer32 (1..2147483647)
    MAX-ACCESS  not-accessible
    STATUS      current
    DESCRIPTION
            "A unique value, greater than zero, for each chassis`s slot6."
    ::= { slot6ModuleEntry 1 }

slot6ModuleId OBJECT-TYPE
    SYNTAX      DisplayString (SIZE (0..32))
    MAX-ACCESS  read-only
    STATUS      current
    DESCRIPTION
            "the value of module`s id"
    ::= { slot6ModuleEntry 2 }
  
slot6ModuleIfNumber OBJECT-TYPE
    SYNTAX      Integer32(0..2147483647)
    MAX-ACCESS  read-only
    STATUS      current
    DESCRIPTION
            "The number of network interfaces (regardless of their
            current state) present on this system." 
    ::= { slot6ModuleEntry 3 } 
    
slot6ModuleIfTable OBJECT-TYPE
    SYNTAX      SEQUENCE OF Slot6ModuleIfEntry
    MAX-ACCESS  not-accessible
    STATUS      current
    DESCRIPTION
            "A list of interface entries.  The number of entries is
            given by the value of ifNumber."
    ::= { slot6Module 2 } 
    
slot6ModuleIfEntry OBJECT-TYPE
    SYNTAX      Slot6ModuleIfEntry
    MAX-ACCESS  not-accessible
    STATUS      current
    DESCRIPTION
            "An entry containing management information applicable to a
            particular interface."
    INDEX   { slot6ModuleifIndex }
    ::= { slot6ModuleIfTable 1 }
    
Slot6ModuleIfEntry ::=
    SEQUENCE {
        slot6ModuleifIndex                 InterfaceIndex,  
        slot6ModuleIfId                    DisplayString,  
        slot6ModuleifDescr                 DisplayString,           
        slot6ModuleifType                  IANAifType,   		
        slot6ModuleifMtu                   Integer32,                
        slot6ModuleifSpeed                 Counter64,               
        slot6ModuleifPhysAddress           PhysAddress,              
        slot6ModuleifAdminStatus           INTEGER,                  
        slot6ModuleifOperStatus            INTEGER,                  
        slot6ModuleifLastChange            TimeTicks,                
        slot6ModuleifInOctets              Counter64,                
        slot6ModuleifInUcastPkts           Counter64,                
        slot6ModuleifInNUcastPkts          Counter64,   
        slot6ModuleifInDiscards            Counter64,
        slot6ModuleifInErrors              Counter64,
        slot6ModuleifInFcsErrorPkts        Counter64,
        slot6ModuleifInUnknownProtos       Counter64,	-- deprecated
        slot6ModuleifOutOctets             Counter64,
        slot6ModuleifOutUcastPkts          Counter64,
        slot6ModuleifOutNUcastPkts         Counter64,  -- deprecated
        slot6ModuleifOutDiscards           Counter64,
        slot6ModuleifOutErrors             Counter64,
        slot6ModuleifOutFcsErrorPkts       Counter64,
        slot6ModuleifOutQLen               Gauge32,    -- deprecated  
        slot6ModuleifOutOctetsRate         Counter64,
        slot6ModuleifInOctetsRate          Counter64,
        slot6ModuleifOutPktsRate           Counter64,
        slot6ModuleifInPktsRate            Counter64,
        slot6ModuleifRxPower               DisplayString,
        slot6ModuleifTxPower               DisplayString,
        slot6ModuleifSpecific              OBJECT IDENTIFIER,
        slot6ModuleifTxMirrorList          DisplayString,
        slot6ModuleifRxMirrorList          DisplayString,
        slot6ModuleifRxPowerMin               DisplayString,
        slot6ModuleifRxPowerMax               DisplayString,
        slot6ModuleifTxPowerMin               DisplayString,
        slot6ModuleifTxPowerMax               DisplayString,
        slot6ModuleifRxHisPeak            Counter64,
        slot6ModuleifTxHisPeak            Counter64,
        slot6ModuleifMode                 DisplayString   		
    }         

slot6ModuleifIndex OBJECT-TYPE
    SYNTAX      InterfaceIndex
    MAX-ACCESS  read-only
    STATUS      current
    DESCRIPTION
            "A unique value, greater than zero, for each interface.  It
            is recommended that values are assigned contiguously
            starting from 1.  The value for each interface sub-layer
            must remain constant at least from one re-initialization of
            the entity's network management system to the next re-
            initialization."
    ::= { slot6ModuleIfEntry 1 }
    
slot6ModuleIfId OBJECT-TYPE
    SYNTAX      DisplayString (SIZE (0..32))
    MAX-ACCESS  read-only
    STATUS      current
    DESCRIPTION
            "the value of module`s id"
    ::= { slot6ModuleIfEntry 2 }
    
slot6ModuleifDescr OBJECT-TYPE
    SYNTAX      DisplayString (SIZE (0..255))
    MAX-ACCESS  read-only
    STATUS      current
    DESCRIPTION
            "A textual string containing information about the
            interface.  This string should include the name of the
            manufacturer, the product name and the version of the
            interface hardware/software."
    ::= { slot6ModuleIfEntry 3 }
    
slot6ModuleifType OBJECT-TYPE
    SYNTAX      IANAifType
    MAX-ACCESS  read-only
    STATUS      current
    DESCRIPTION
            "The type of interface.  Additional values for ifType are
            assigned by the Internet Assigned Numbers Authority (IANA),
            through updating the syntax of the IANAifType textual
            convention."
    ::= { slot6ModuleIfEntry 4 }

slot6ModuleifMtu OBJECT-TYPE
    SYNTAX      Integer32(1..2147483647)
    MAX-ACCESS  read-only
    STATUS      current
    DESCRIPTION
            "The size of the largest packet which can be sent/received
            on the interface, specified in octets.  For interfaces that
            are used for transmitting network datagrams, this is the
            size of the largest network datagram that can be sent on the
            interface."
    ::= { slot6ModuleIfEntry 5 }

slot6ModuleifSpeed OBJECT-TYPE
    SYNTAX      Counter64
    MAX-ACCESS  read-only
    STATUS      current
    DESCRIPTION
            "An estimate of the interface's current bandwidth in bits
            per second.  For interfaces which do not vary in bandwidth
            or for those where no accurate estimation can be made, this
            object should contain the nominal bandwidth. For a sub-layer
            which has no concept of bandwidth, this object should be zero."
    ::= { slot6ModuleIfEntry 6 }

slot6ModuleifPhysAddress OBJECT-TYPE
    SYNTAX      PhysAddress
    MAX-ACCESS  read-only
    STATUS      current
    DESCRIPTION
            "The interface's address at its protocol sub-layer.  For
            example, for an 802.x interface, this object normally
            contains a MAC address.  The interface's media-specific MIB
            must define the bit and byte ordering and the format of the
            value of this object.  For interfaces which do not have such
            an address (e.g., a serial line), this object should contain
            an octet string of zero length."
    ::= { slot6ModuleIfEntry 7 }
    
slot6ModuleifAdminStatus OBJECT-TYPE
    SYNTAX  INTEGER {
                up(1),       -- ready to pass packets
                down(2),
                testing(3)   -- in some test mode
            }
    MAX-ACCESS  read-write
    STATUS      current
    DESCRIPTION
            "The desired state of the interface.  The testing(3) state
            indicates that no operational packets can be passed.  When a
            managed system initializes, all interfaces start with
            ifAdminStatus in the down(2) state.  As a result of either
            explicit management action or per configuration information
            retained by the managed system, ifAdminStatus is then
            changed to either the up(1) or testing(3) states (or remains
            in the down(2) state)."
    ::= { slot6ModuleIfEntry 8 }

slot6ModuleifOperStatus OBJECT-TYPE
    SYNTAX  INTEGER {
                up(1),        -- ready to pass packets
                down(2),
                testing(3),   -- in some test mode
                unknown(4),   -- status can not be determined
                              -- for some reason.
                dormant(5),
                notPresent(6),    -- some component is missing
                lowerLayerDown(7) -- down due to state of
                                  -- lower-layer interface(s)
            }
    MAX-ACCESS  read-only
    STATUS      current
    DESCRIPTION
            "The current operational state of the interface.  The
            testing(3) state indicates that no operational packets can
            be passed.  If ifAdminStatus is down(2) then ifOperStatus
            should be down(2).  If ifAdminStatus is changed to up(1)
            then ifOperStatus should change to up(1) if the interface is
            ready to transmit and receive network traffic; it should
            change to dormant(5) if the interface is waiting for
            external actions (such as a serial line waiting for an
            incoming connection); it should remain in the down(2) state
            if and only if there is a fault that prevents it from going
            to the up(1) state; it should remain in the notPresent(6)
            state if the interface has missing (typically, hardware)
            components."
    ::= { slot6ModuleIfEntry 9 }

slot6ModuleifLastChange OBJECT-TYPE
    SYNTAX      TimeTicks
    MAX-ACCESS  read-only
    STATUS      current
    DESCRIPTION
            "The value of sysUpTime at the time the interface entered
            its current operational state.  If the current state was
            entered prior to the last re-initialization of the local
            network management subsystem, then this object contains a
            zero value."
    ::= { slot6ModuleIfEntry 10 }

slot6ModuleifInOctets OBJECT-TYPE
    SYNTAX      Counter64
    MAX-ACCESS  read-only
    STATUS      current
    DESCRIPTION
            "The total number of octets received on the interface,
            including framing characters.

            Discontinuities in the value of this counter can occur at
            re-initialization of the management system, and at other
            times as indicated by the value of
            ifCounterDiscontinuityTime."
    ::= { slot6ModuleIfEntry 11 }

slot6ModuleifInUcastPkts OBJECT-TYPE
    SYNTAX      Counter64
    MAX-ACCESS  read-only
    STATUS      current
    DESCRIPTION
            "The number of packets, delivered by this sub-layer to a
            higher (sub-)layer, which were not addressed to a multicast
            or broadcast address at this sub-layer.

            Discontinuities in the value of this counter can occur at
            re-initialization of the management system, and at other
            times as indicated by the value of
            ifCounterDiscontinuityTime."
    ::= { slot6ModuleIfEntry 12 }

slot6ModuleifInNUcastPkts OBJECT-TYPE
    SYNTAX  Counter64
    MAX-ACCESS  read-only
    STATUS      current
    DESCRIPTION
            "The number of packets, delivered by this sub-layer to a
            higher (sub-)layer, which were addressed to a multicast or
            broadcast address at this sub-layer.

            Discontinuities in the value of this counter can occur at
            re-initialization of the management system, and at other
            times as indicated by the value of
            ifCounterDiscontinuityTime.

            This object is deprecated in favour of ifInMulticastPkts and
            ifInBroadcastPkts."
    ::= { slot6ModuleIfEntry 13 }

slot6ModuleifInDiscards OBJECT-TYPE
    SYNTAX      Counter64
    MAX-ACCESS  read-only
    STATUS      current
    DESCRIPTION
            "The number of inbound packets which were chosen to be
            discarded even though no errors had been detected to prevent

            their being deliverable to a higher-layer protocol.  One
            possible reason for discarding such a packet could be to
            free up buffer space.

            Discontinuities in the value of this counter can occur at
            re-initialization of the management system, and at other
            times as indicated by the value of
            ifCounterDiscontinuityTime."
    ::= { slot6ModuleIfEntry 14 }

slot6ModuleifInErrors OBJECT-TYPE
    SYNTAX      Counter64
    MAX-ACCESS  read-only
    STATUS      current
    DESCRIPTION
            "For packet-oriented interfaces, the number of inbound
            packets that contained errors preventing them from being
            deliverable to a higher-layer protocol.  For character-
            oriented or fixed-length interfaces, the number of inbound
            transmission units that contained errors preventing them
            from being deliverable to a higher-layer protocol.

            Discontinuities in the value of this counter can occur at
            re-initialization of the management system, and at other
            times as indicated by the value of
            ifCounterDiscontinuityTime."
    ::= { slot6ModuleIfEntry 15 }

slot6ModuleifInFcsErrorPkts OBJECT-TYPE
    SYNTAX      Counter64
    MAX-ACCESS  read-only
    STATUS      current
    DESCRIPTION
            "FCS error pakets."
    ::= { slot6ModuleIfEntry 16 }

slot6ModuleifInUnknownProtos OBJECT-TYPE
    SYNTAX      Counter64
    MAX-ACCESS  read-only
    STATUS      current
    DESCRIPTION
            "For packet-oriented interfaces, the number of packets
            received via the interface which were discarded because of
            an unknown or unsupported protocol.  For character-oriented
            or fixed-length interfaces that support protocol
            multiplexing the number of transmission units received via
            the interface which were discarded because of an unknown or
            unsupported protocol.  For any interface that does not
            support protocol multiplexing, this counter will always be
            0.

            Discontinuities in the value of this counter can occur at
            re-initialization of the management system, and at other
            times as indicated by the value of
            ifCounterDiscontinuityTime."
    ::= { slot6ModuleIfEntry 17 }

slot6ModuleifOutOctets OBJECT-TYPE
    SYNTAX      Counter64
    MAX-ACCESS  read-only
    STATUS      current
    DESCRIPTION
            "The total number of octets transmitted out of the
            interface, including framing characters.

            Discontinuities in the value of this counter can occur at
            re-initialization of the management system, and at other
            times as indicated by the value of
            ifCounterDiscontinuityTime."
    ::= { slot6ModuleIfEntry 18 }

slot6ModuleifOutUcastPkts OBJECT-TYPE
    SYNTAX      Counter64
    MAX-ACCESS  read-only
    STATUS      current
    DESCRIPTION
            "The total number of packets that higher-level protocols
            requested be transmitted, and which were not addressed to a
            multicast or broadcast address at this sub-layer, including
            those that were discarded or not sent.

            Discontinuities in the value of this counter can occur at
            re-initialization of the management system, and at other
            times as indicated by the value of
            ifCounterDiscontinuityTime."
    ::= { slot6ModuleIfEntry 19 }

slot6ModuleifOutNUcastPkts OBJECT-TYPE
    SYNTAX      Counter64
    MAX-ACCESS  read-only
    STATUS      deprecated
    DESCRIPTION
            "The total number of packets that higher-level protocols
            requested be transmitted, and which were addressed to a
            multicast or broadcast address at this sub-layer, including
            those that were discarded or not sent.

            Discontinuities in the value of this counter can occur at
            re-initialization of the management system, and at other
            times as indicated by the value of
            ifCounterDiscontinuityTime.

            This object is deprecated in favour of ifOutMulticastPkts
            and ifOutBroadcastPkts."
    ::= { slot6ModuleIfEntry 20 }

slot6ModuleifOutDiscards OBJECT-TYPE
    SYNTAX      Counter64
    MAX-ACCESS  read-only
    STATUS      current
    DESCRIPTION
            "The number of outbound packets which were chosen to be
            discarded even though no errors had been detected to prevent
            their being transmitted.  One possible reason for discarding
            such a packet could be to free up buffer space.

            Discontinuities in the value of this counter can occur at
            re-initialization of the management system, and at other
            times as indicated by the value of
            ifCounterDiscontinuityTime."
    ::= { slot6ModuleIfEntry 21 }

slot6ModuleifOutErrors OBJECT-TYPE
    SYNTAX      Counter64
    MAX-ACCESS  read-only
    STATUS      current
    DESCRIPTION
            "For packet-oriented interfaces, the number of outbound
            packets that could not be transmitted because of errors.
            For character-oriented or fixed-length interfaces, the
            number of outbound transmission units that could not be
            transmitted because of errors.

            Discontinuities in the value of this counter can occur at
            re-initialization of the management system, and at other
            times as indicated by the value of
            ifCounterDiscontinuityTime."
    ::= { slot6ModuleIfEntry 22 }

slot6ModuleifOutFcsErrorPkts OBJECT-TYPE
    SYNTAX      Counter64
    MAX-ACCESS  read-only
    STATUS      current
    DESCRIPTION
            "FCS error pakets."
    ::= { slot6ModuleIfEntry 23 }

slot6ModuleifOutQLen OBJECT-TYPE
    SYNTAX      Gauge32
    MAX-ACCESS  read-only
    STATUS      deprecated
    DESCRIPTION
            "The length of the output packet queue (in packets)."
    ::= { slot6ModuleIfEntry 24 }

slot6ModuleifOutOctetsRate OBJECT-TYPE
    SYNTAX      Counter64
    MAX-ACCESS  read-only
    STATUS      current
    DESCRIPTION
            "The speed of octets trans on the interface(kbps)"
    ::= { slot6ModuleIfEntry 25 }

slot6ModuleifInOctetsRate OBJECT-TYPE
    SYNTAX      Counter64
    MAX-ACCESS  read-only
    STATUS      current
    DESCRIPTION
            "The speed of octets received on the interface(kbps)"
    ::= { slot6ModuleIfEntry 26 }

slot6ModuleifOutPktsRate OBJECT-TYPE
    SYNTAX      Counter64
    MAX-ACCESS  read-only
    STATUS      current
    DESCRIPTION
            "The speed of packets trans on the interface(pps)"
    ::= { slot6ModuleIfEntry 27 }

slot6ModuleifInPktsRate OBJECT-TYPE
    SYNTAX      Counter64
    MAX-ACCESS  read-only
    STATUS      current
    DESCRIPTION
            "The speed of octets received on the interface(kbps)"
    ::= { slot6ModuleIfEntry 28 }

slot6ModuleifRxPower OBJECT-TYPE
    SYNTAX      DisplayString (SIZE (0..255))
    MAX-ACCESS  read-only
    STATUS      current
    DESCRIPTION
            "the value of interface's received power, in dbm format."
    ::= { slot6ModuleIfEntry 29 }

slot6ModuleifTxPower OBJECT-TYPE
    SYNTAX      DisplayString (SIZE (0..255))
    MAX-ACCESS  read-only
    STATUS      current
    DESCRIPTION
            "the value of interface's send power, in dbm format."
    ::= { slot6ModuleIfEntry 30 }

slot6ModuleifSpecific OBJECT-TYPE
    SYNTAX      OBJECT IDENTIFIER
    MAX-ACCESS  read-only
    STATUS      deprecated
    DESCRIPTION
            "A reference to MIB definitions specific to the particular
            media being used to realize the interface.  It is

            recommended that this value point to an instance of a MIB
            object in the media-specific MIB, i.e., that this object
            have the semantics associated with the InstancePointer
            textual convention defined in RFC 2579.  In fact, it is
            recommended that the media-specific MIB specify what value
            ifSpecific should/can take for values of ifType.  If no MIB
            definitions specific to the particular media are available,
            the value should be set to the OBJECT IDENTIFIER { 0 0 }."
    ::= { slot6ModuleIfEntry 31 }  
      
slot6ModuleifTxMirrorList OBJECT-TYPE
    SYNTAX      DisplayString (SIZE (0..255))
    MAX-ACCESS  read-only
    STATUS      deprecated
    DESCRIPTION
            "the interface tx mirror list."
    ::= { slot6ModuleIfEntry 32 }  
 
slot6ModuleifRxMirrorList OBJECT-TYPE
    SYNTAX      DisplayString (SIZE (0..255))
    MAX-ACCESS  read-only
    STATUS      deprecated
    DESCRIPTION
            "the interface rx mirror list."
    ::= { slot6ModuleIfEntry 33 }  

slot6ModuleifRxPowerMin OBJECT-TYPE
    SYNTAX      DisplayString (SIZE (0..255))
    MAX-ACCESS  read-only
    STATUS      deprecated
    DESCRIPTION
            "the interface min rx power."
    ::= { slot6ModuleIfEntry 34 }  

slot6ModuleifRxPowerMax OBJECT-TYPE
    SYNTAX      DisplayString (SIZE (0..255))
    MAX-ACCESS  read-only
    STATUS      deprecated
    DESCRIPTION
            "the interface max rx power."
    ::= { slot6ModuleIfEntry 35 }  

slot6ModuleifTxPowerMin OBJECT-TYPE
    SYNTAX      DisplayString (SIZE (0..255))
    MAX-ACCESS  read-only
    STATUS      deprecated
    DESCRIPTION
            "the interface min tx power."
    ::= { slot6ModuleIfEntry 36 }  

slot6ModuleifTxPowerMax OBJECT-TYPE
    SYNTAX      DisplayString (SIZE (0..255))
    MAX-ACCESS  read-only
    STATUS      deprecated
    DESCRIPTION
            "the interface max tx power."
    ::= { slot6ModuleIfEntry 37 }  

slot6ModuleifRxHisPeak OBJECT-TYPE
    SYNTAX      Counter64
    MAX-ACCESS  read-only
    STATUS      current
    DESCRIPTION
            "The max speed of rx rate on the interface(kbps)"
    ::= { slot6ModuleIfEntry 38 }

slot6ModuleifTxHisPeak OBJECT-TYPE
    SYNTAX      Counter64
    MAX-ACCESS  read-only
    STATUS      current
    DESCRIPTION
            "The max speed of tx rate on the interface(kbps)"
    ::= { slot6ModuleIfEntry 39 }

slot6ModuleifMode OBJECT-TYPE
    SYNTAX      DisplayString (SIZE (0..255))
    MAX-ACCESS  read-only
    STATUS      deprecated
    DESCRIPTION
            "the interface if mode."
    ::= { slot6ModuleIfEntry 40 }  

-- slot 7 --

-- slot7Table --

slot7Table OBJECT-TYPE
    SYNTAX      SEQUENCE OF Slot7Entry
    MAX-ACCESS  not-accessible
    STATUS      current
    DESCRIPTION
            "A list of all slot7Type's utilization."
    ::= { slot7 1 }  

slot7Entry OBJECT-TYPE
    SYNTAX      Slot7Entry
    MAX-ACCESS  not-accessible
    STATUS      current
    DESCRIPTION
            "An entry contains a slot7's utilization."
    INDEX   { slot7Index }
    ::= { slot7Table 1 }

Slot7Entry ::=
    SEQUENCE {     
		slot7Index                       Integer32,
		slot7Type                        DisplayString,
		slot7Status                      DisplayString,		
        slot7SerialNumber                DisplayString,		
        slot7Temperature                 DisplayString
    }  

slot7Index OBJECT-TYPE
    SYNTAX      Integer32 (1..2147483647)
    MAX-ACCESS  not-accessible
    STATUS      current
    DESCRIPTION
            "A unique value, greater than zero, for each chassis`s slot7."
    ::= { slot7Entry 1 }

slot7Type OBJECT-TYPE
    SYNTAX      DisplayString (SIZE (0..255))
    MAX-ACCESS  read-only
    STATUS      current
    DESCRIPTION
            "the slot7Type of each chassis."
    ::= { slot7Entry 2 }

slot7Status OBJECT-TYPE
    SYNTAX      DisplayString (SIZE (0..255))
    MAX-ACCESS  read-only
    STATUS      current
    DESCRIPTION
            "A string to describe the board status." 
    ::= { slot7Entry 3 }   


slot7SerialNumber OBJECT-TYPE
    SYNTAX      DisplayString (SIZE (0..255))
    MAX-ACCESS  read-only
    STATUS      current
    DESCRIPTION
            "A string to describe the board serial number." 
    ::= { slot7Entry 4 }   

slot7Temperature OBJECT-TYPE
    SYNTAX      DisplayString (SIZE (0..255))
    MAX-ACCESS  read-only
    STATUS      current
    DESCRIPTION
            "A string to describe the board temperature." 
    ::= { slot7Entry 5 }   


slot7Module OBJECT IDENTIFIER ::= { slot7 2 }

-- slot7ModuleTable --
slot7ModuleTable OBJECT-TYPE
    SYNTAX      SEQUENCE OF Slot7ModuleEntry
    MAX-ACCESS  not-accessible
    STATUS      current
    DESCRIPTION
            "A list of all slot7Module's utilization."
    ::= { slot7Module 1 }  

slot7ModuleEntry OBJECT-TYPE
    SYNTAX      Slot7ModuleEntry
    MAX-ACCESS  not-accessible
    STATUS      current
    DESCRIPTION
            "An entry contains a slot7Module's utilization."
    INDEX   { slot7ModuleIndex }
    ::= { slot7ModuleTable 1 }

Slot7ModuleEntry ::=
    SEQUENCE {     
		slot7ModuleIndex                       Integer32,
		slot7ModuleId                           DisplayString,  
		slot7ModuleIfNumber                     Integer32		
    } 

slot7ModuleIndex OBJECT-TYPE
    SYNTAX      Integer32 (1..2147483647)
    MAX-ACCESS  not-accessible
    STATUS      current
    DESCRIPTION
            "A unique value, greater than zero, for each chassis`s slot7."
    ::= { slot7ModuleEntry 1 }

slot7ModuleId OBJECT-TYPE
    SYNTAX      DisplayString (SIZE (0..32))
    MAX-ACCESS  read-only
    STATUS      current
    DESCRIPTION
            "the value of module`s id"
    ::= { slot7ModuleEntry 2 }
  
slot7ModuleIfNumber OBJECT-TYPE
    SYNTAX      Integer32(0..2147483647)
    MAX-ACCESS  read-only
    STATUS      current
    DESCRIPTION
            "The number of network interfaces (regardless of their
            current state) present on this system." 
    ::= { slot7ModuleEntry 3 } 
    
slot7ModuleIfTable OBJECT-TYPE
    SYNTAX      SEQUENCE OF Slot7ModuleIfEntry
    MAX-ACCESS  not-accessible
    STATUS      current
    DESCRIPTION
            "A list of interface entries.  The number of entries is
            given by the value of ifNumber."
    ::= { slot7Module 2 } 
    
slot7ModuleIfEntry OBJECT-TYPE
    SYNTAX      Slot7ModuleIfEntry
    MAX-ACCESS  not-accessible
    STATUS      current
    DESCRIPTION
            "An entry containing management information applicable to a
            particular interface."
    INDEX   { slot7ModuleifIndex }
    ::= { slot7ModuleIfTable 1 }
    
Slot7ModuleIfEntry ::=
    SEQUENCE {
        slot7ModuleifIndex                 InterfaceIndex,  
        slot7ModuleIfId                    DisplayString,  
        slot7ModuleifDescr                 DisplayString,           
        slot7ModuleifType                  IANAifType,   		
        slot7ModuleifMtu                   Integer32,                
        slot7ModuleifSpeed                 Counter64,               
        slot7ModuleifPhysAddress           PhysAddress,              
        slot7ModuleifAdminStatus           INTEGER,                  
        slot7ModuleifOperStatus            INTEGER,                  
        slot7ModuleifLastChange            TimeTicks,                
        slot7ModuleifInOctets              Counter64,                
        slot7ModuleifInUcastPkts           Counter64,                
        slot7ModuleifInNUcastPkts          Counter64,    
        slot7ModuleifInDiscards            Counter64,
        slot7ModuleifInErrors              Counter64,
        slot7ModuleifInFcsErrorPkts        Counter64,
        slot7ModuleifInUnknownProtos       Counter64,	-- deprecated
        slot7ModuleifOutOctets             Counter64,
        slot7ModuleifOutUcastPkts          Counter64,
        slot7ModuleifOutNUcastPkts         Counter64,  -- deprecated
        slot7ModuleifOutDiscards           Counter64,
        slot7ModuleifOutErrors             Counter64,
        slot7ModuleifOutFcsErrorPkts       Counter64,
        slot7ModuleifOutQLen               Gauge32,    -- deprecated  
        slot7ModuleifOutOctetsRate         Counter64,
        slot7ModuleifInOctetsRate          Counter64,
        slot7ModuleifOutPktsRate           Counter64,
        slot7ModuleifInPktsRate            Counter64,
        slot7ModuleifRxPower               DisplayString,
        slot7ModuleifTxPower               DisplayString,
        slot7ModuleifSpecific              OBJECT IDENTIFIER,
        slot7ModuleifTxMirrorList          DisplayString,
        slot7ModuleifRxMirrorList          DisplayString,
        slot7ModuleifRxPowerMin               DisplayString,
        slot7ModuleifRxPowerMax               DisplayString,
        slot7ModuleifTxPowerMin               DisplayString,
        slot7ModuleifTxPowerMax               DisplayString,
        slot7ModuleifRxHisPeak            Counter64,
        slot7ModuleifTxHisPeak            Counter64,
        slot7ModuleifMode                 DisplayString   		
    }         

slot7ModuleifIndex OBJECT-TYPE
    SYNTAX      InterfaceIndex
    MAX-ACCESS  read-only
    STATUS      current
    DESCRIPTION
            "A unique value, greater than zero, for each interface.  It
            is recommended that values are assigned contiguously
            starting from 1.  The value for each interface sub-layer
            must remain constant at least from one re-initialization of
            the entity's network management system to the next re-
            initialization."
    ::= { slot7ModuleIfEntry 1 }
    
slot7ModuleIfId OBJECT-TYPE
    SYNTAX      DisplayString (SIZE (0..32))
    MAX-ACCESS  read-only
    STATUS      current
    DESCRIPTION
            "the value of module`s id"
    ::= { slot7ModuleIfEntry 2 }
    
slot7ModuleifDescr OBJECT-TYPE
    SYNTAX      DisplayString (SIZE (0..255))
    MAX-ACCESS  read-only
    STATUS      current
    DESCRIPTION
            "A textual string containing information about the
            interface.  This string should include the name of the
            manufacturer, the product name and the version of the
            interface hardware/software."
    ::= { slot7ModuleIfEntry 3 }
    
slot7ModuleifType OBJECT-TYPE
    SYNTAX      IANAifType
    MAX-ACCESS  read-only
    STATUS      current
    DESCRIPTION
            "The type of interface.  Additional values for ifType are
            assigned by the Internet Assigned Numbers Authority (IANA),
            through updating the syntax of the IANAifType textual
            convention."
    ::= { slot7ModuleIfEntry 4 }

slot7ModuleifMtu OBJECT-TYPE
    SYNTAX      Integer32(1..2147483647)
    MAX-ACCESS  read-only
    STATUS      current
    DESCRIPTION
            "The size of the largest packet which can be sent/received
            on the interface, specified in octets.  For interfaces that
            are used for transmitting network datagrams, this is the
            size of the largest network datagram that can be sent on the
            interface."
    ::= { slot7ModuleIfEntry 5 }

slot7ModuleifSpeed OBJECT-TYPE
    SYNTAX      Counter64
    MAX-ACCESS  read-only
    STATUS      current
    DESCRIPTION
            "An estimate of the interface's current bandwidth in bits
            per second.  For interfaces which do not vary in bandwidth
            or for those where no accurate estimation can be made, this
            object should contain the nominal bandwidth. For a sub-layer
            which has no concept of bandwidth, this object should be zero."
    ::= { slot7ModuleIfEntry 6 }

slot7ModuleifPhysAddress OBJECT-TYPE
    SYNTAX      PhysAddress
    MAX-ACCESS  read-only
    STATUS      current
    DESCRIPTION
            "The interface's address at its protocol sub-layer.  For
            example, for an 802.x interface, this object normally
            contains a MAC address.  The interface's media-specific MIB
            must define the bit and byte ordering and the format of the
            value of this object.  For interfaces which do not have such
            an address (e.g., a serial line), this object should contain
            an octet string of zero length."
    ::= { slot7ModuleIfEntry 7 }
    
slot7ModuleifAdminStatus OBJECT-TYPE
    SYNTAX  INTEGER {
                up(1),       -- ready to pass packets
                down(2),
                testing(3)   -- in some test mode
            }
    MAX-ACCESS  read-write
    STATUS      current
    DESCRIPTION
            "The desired state of the interface.  The testing(3) state
            indicates that no operational packets can be passed.  When a
            managed system initializes, all interfaces start with
            ifAdminStatus in the down(2) state.  As a result of either
            explicit management action or per configuration information
            retained by the managed system, ifAdminStatus is then
            changed to either the up(1) or testing(3) states (or remains
            in the down(2) state)."
    ::= { slot7ModuleIfEntry 8 }

slot7ModuleifOperStatus OBJECT-TYPE
    SYNTAX  INTEGER {
                up(1),        -- ready to pass packets
                down(2),
                testing(3),   -- in some test mode
                unknown(4),   -- status can not be determined
                              -- for some reason.
                dormant(5),
                notPresent(6),    -- some component is missing
                lowerLayerDown(7) -- down due to state of
                                  -- lower-layer interface(s)
            }
    MAX-ACCESS  read-only
    STATUS      current
    DESCRIPTION
            "The current operational state of the interface.  The
            testing(3) state indicates that no operational packets can
            be passed.  If ifAdminStatus is down(2) then ifOperStatus
            should be down(2).  If ifAdminStatus is changed to up(1)
            then ifOperStatus should change to up(1) if the interface is
            ready to transmit and receive network traffic; it should
            change to dormant(5) if the interface is waiting for
            external actions (such as a serial line waiting for an
            incoming connection); it should remain in the down(2) state
            if and only if there is a fault that prevents it from going
            to the up(1) state; it should remain in the notPresent(6)
            state if the interface has missing (typically, hardware)
            components."
    ::= { slot7ModuleIfEntry 9 }

slot7ModuleifLastChange OBJECT-TYPE
    SYNTAX      TimeTicks
    MAX-ACCESS  read-only
    STATUS      current
    DESCRIPTION
            "The value of sysUpTime at the time the interface entered
            its current operational state.  If the current state was
            entered prior to the last re-initialization of the local
            network management subsystem, then this object contains a
            zero value."
    ::= { slot7ModuleIfEntry 10 }

slot7ModuleifInOctets OBJECT-TYPE
    SYNTAX      Counter64
    MAX-ACCESS  read-only
    STATUS      current
    DESCRIPTION
            "The total number of octets received on the interface,
            including framing characters.

            Discontinuities in the value of this counter can occur at
            re-initialization of the management system, and at other
            times as indicated by the value of
            ifCounterDiscontinuityTime."
    ::= { slot7ModuleIfEntry 11 }

slot7ModuleifInUcastPkts OBJECT-TYPE
    SYNTAX      Counter64
    MAX-ACCESS  read-only
    STATUS      current
    DESCRIPTION
            "The number of packets, delivered by this sub-layer to a
            higher (sub-)layer, which were not addressed to a multicast
            or broadcast address at this sub-layer.

            Discontinuities in the value of this counter can occur at
            re-initialization of the management system, and at other
            times as indicated by the value of
            ifCounterDiscontinuityTime."
    ::= { slot7ModuleIfEntry 12 }

slot7ModuleifInNUcastPkts OBJECT-TYPE
    SYNTAX  Counter64
    MAX-ACCESS  read-only
    STATUS      current
    DESCRIPTION
            "The number of packets, delivered by this sub-layer to a
            higher (sub-)layer, which were addressed to a multicast or
            broadcast address at this sub-layer.

            Discontinuities in the value of this counter can occur at
            re-initialization of the management system, and at other
            times as indicated by the value of
            ifCounterDiscontinuityTime.

            This object is deprecated in favour of ifInMulticastPkts and
            ifInBroadcastPkts."
    ::= { slot7ModuleIfEntry 13 }

slot7ModuleifInDiscards OBJECT-TYPE
    SYNTAX      Counter64
    MAX-ACCESS  read-only
    STATUS      current
    DESCRIPTION
            "The number of inbound packets which were chosen to be
            discarded even though no errors had been detected to prevent

            their being deliverable to a higher-layer protocol.  One
            possible reason for discarding such a packet could be to
            free up buffer space.

            Discontinuities in the value of this counter can occur at
            re-initialization of the management system, and at other
            times as indicated by the value of
            ifCounterDiscontinuityTime."
    ::= { slot7ModuleIfEntry 14 }

slot7ModuleifInErrors OBJECT-TYPE
    SYNTAX      Counter64
    MAX-ACCESS  read-only
    STATUS      current
    DESCRIPTION
            "For packet-oriented interfaces, the number of inbound
            packets that contained errors preventing them from being
            deliverable to a higher-layer protocol.  For character-
            oriented or fixed-length interfaces, the number of inbound
            transmission units that contained errors preventing them
            from being deliverable to a higher-layer protocol.

            Discontinuities in the value of this counter can occur at
            re-initialization of the management system, and at other
            times as indicated by the value of
            ifCounterDiscontinuityTime."
    ::= { slot7ModuleIfEntry 15 }

slot7ModuleifInFcsErrorPkts OBJECT-TYPE
    SYNTAX      Counter64
    MAX-ACCESS  read-only
    STATUS      current
    DESCRIPTION
            "FCS error pakets."
    ::= { slot7ModuleIfEntry 16 }

slot7ModuleifInUnknownProtos OBJECT-TYPE
    SYNTAX      Counter64
    MAX-ACCESS  read-only
    STATUS      current
    DESCRIPTION
            "For packet-oriented interfaces, the number of packets
            received via the interface which were discarded because of
            an unknown or unsupported protocol.  For character-oriented
            or fixed-length interfaces that support protocol
            multiplexing the number of transmission units received via
            the interface which were discarded because of an unknown or
            unsupported protocol.  For any interface that does not
            support protocol multiplexing, this counter will always be
            0.

            Discontinuities in the value of this counter can occur at
            re-initialization of the management system, and at other
            times as indicated by the value of
            ifCounterDiscontinuityTime."
    ::= { slot7ModuleIfEntry 17 }

slot7ModuleifOutOctets OBJECT-TYPE
    SYNTAX      Counter64
    MAX-ACCESS  read-only
    STATUS      current
    DESCRIPTION
            "The total number of octets transmitted out of the
            interface, including framing characters.

            Discontinuities in the value of this counter can occur at
            re-initialization of the management system, and at other
            times as indicated by the value of
            ifCounterDiscontinuityTime."
    ::= { slot7ModuleIfEntry 18 }

slot7ModuleifOutUcastPkts OBJECT-TYPE
    SYNTAX      Counter64
    MAX-ACCESS  read-only
    STATUS      current
    DESCRIPTION
            "The total number of packets that higher-level protocols
            requested be transmitted, and which were not addressed to a
            multicast or broadcast address at this sub-layer, including
            those that were discarded or not sent.

            Discontinuities in the value of this counter can occur at
            re-initialization of the management system, and at other
            times as indicated by the value of
            ifCounterDiscontinuityTime."
    ::= { slot7ModuleIfEntry 19 }

slot7ModuleifOutNUcastPkts OBJECT-TYPE
    SYNTAX      Counter64
    MAX-ACCESS  read-only
    STATUS      deprecated
    DESCRIPTION
            "The total number of packets that higher-level protocols
            requested be transmitted, and which were addressed to a
            multicast or broadcast address at this sub-layer, including
            those that were discarded or not sent.

            Discontinuities in the value of this counter can occur at
            re-initialization of the management system, and at other
            times as indicated by the value of
            ifCounterDiscontinuityTime.

            This object is deprecated in favour of ifOutMulticastPkts
            and ifOutBroadcastPkts."
    ::= { slot7ModuleIfEntry 20 }

slot7ModuleifOutDiscards OBJECT-TYPE
    SYNTAX      Counter64
    MAX-ACCESS  read-only
    STATUS      current
    DESCRIPTION
            "The number of outbound packets which were chosen to be
            discarded even though no errors had been detected to prevent
            their being transmitted.  One possible reason for discarding
            such a packet could be to free up buffer space.

            Discontinuities in the value of this counter can occur at
            re-initialization of the management system, and at other
            times as indicated by the value of
            ifCounterDiscontinuityTime."
    ::= { slot7ModuleIfEntry 21 }

slot7ModuleifOutErrors OBJECT-TYPE
    SYNTAX      Counter64
    MAX-ACCESS  read-only
    STATUS      current
    DESCRIPTION
            "For packet-oriented interfaces, the number of outbound
            packets that could not be transmitted because of errors.
            For character-oriented or fixed-length interfaces, the
            number of outbound transmission units that could not be
            transmitted because of errors.

            Discontinuities in the value of this counter can occur at
            re-initialization of the management system, and at other
            times as indicated by the value of
            ifCounterDiscontinuityTime."
    ::= { slot7ModuleIfEntry 22 }

slot7ModuleifOutFcsErrorPkts OBJECT-TYPE
    SYNTAX      Counter64
    MAX-ACCESS  read-only
    STATUS      current
    DESCRIPTION
            "FCS error pakets."
    ::= { slot7ModuleIfEntry 23 }

slot7ModuleifOutQLen OBJECT-TYPE
    SYNTAX      Gauge32
    MAX-ACCESS  read-only
    STATUS      deprecated
    DESCRIPTION
            "The length of the output packet queue (in packets)."
    ::= { slot7ModuleIfEntry 24 }

slot7ModuleifOutOctetsRate OBJECT-TYPE
    SYNTAX      Counter64
    MAX-ACCESS  read-only
    STATUS      current
    DESCRIPTION
            "The speed of octets trans on the interface(kbps)"
    ::= { slot7ModuleIfEntry 25 }

slot7ModuleifInOctetsRate OBJECT-TYPE
    SYNTAX      Counter64
    MAX-ACCESS  read-only
    STATUS      current
    DESCRIPTION
            "The speed of octets received on the interface(kbps)"
    ::= { slot7ModuleIfEntry 26 }

slot7ModuleifOutPktsRate OBJECT-TYPE
    SYNTAX      Counter64
    MAX-ACCESS  read-only
    STATUS      current
    DESCRIPTION
            "The speed of packets trans on the interface(pps)"
    ::= { slot7ModuleIfEntry 27 }

slot7ModuleifInPktsRate OBJECT-TYPE
    SYNTAX      Counter64
    MAX-ACCESS  read-only
    STATUS      current
    DESCRIPTION
            "The speed of octets received on the interface(kbps)"
    ::= { slot7ModuleIfEntry 28 }

slot7ModuleifRxPower OBJECT-TYPE
    SYNTAX      DisplayString (SIZE (0..255))
    MAX-ACCESS  read-only
    STATUS      current
    DESCRIPTION
            "the value of interface's received power, in dbm format."
    ::= { slot7ModuleIfEntry 29 }

slot7ModuleifTxPower OBJECT-TYPE
    SYNTAX      DisplayString (SIZE (0..255))
    MAX-ACCESS  read-only
    STATUS      current
    DESCRIPTION
            "the value of interface's send power, in dbm format."
    ::= { slot7ModuleIfEntry 30 }

slot7ModuleifSpecific OBJECT-TYPE
    SYNTAX      OBJECT IDENTIFIER
    MAX-ACCESS  read-only
    STATUS      deprecated
    DESCRIPTION
            "A reference to MIB definitions specific to the particular
            media being used to realize the interface.  It is

            recommended that this value point to an instance of a MIB
            object in the media-specific MIB, i.e., that this object
            have the semantics associated with the InstancePointer
            textual convention defined in RFC 2579.  In fact, it is
            recommended that the media-specific MIB specify what value
            ifSpecific should/can take for values of ifType.  If no MIB
            definitions specific to the particular media are available,
            the value should be set to the OBJECT IDENTIFIER { 0 0 }."
    ::= { slot7ModuleIfEntry 31 }  
   
slot7ModuleifTxMirrorList OBJECT-TYPE
    SYNTAX      DisplayString (SIZE (0..255))
    MAX-ACCESS  read-only
    STATUS      deprecated
    DESCRIPTION
            "the interface tx mirror list."
    ::= { slot7ModuleIfEntry 32 }  
 
slot7ModuleifRxMirrorList OBJECT-TYPE
    SYNTAX      DisplayString (SIZE (0..255))
    MAX-ACCESS  read-only
    STATUS      deprecated
    DESCRIPTION
            "the interface rx mirror list."
    ::= { slot7ModuleIfEntry 33 }  
  
slot7ModuleifRxPowerMin OBJECT-TYPE
    SYNTAX      DisplayString (SIZE (0..255))
    MAX-ACCESS  read-only
    STATUS      deprecated
    DESCRIPTION
            "the interface min rx power."
    ::= { slot7ModuleIfEntry 34 }  

slot7ModuleifRxPowerMax OBJECT-TYPE
    SYNTAX      DisplayString (SIZE (0..255))
    MAX-ACCESS  read-only
    STATUS      deprecated
    DESCRIPTION
            "the interface max rx power."
    ::= { slot7ModuleIfEntry 35 }  

slot7ModuleifTxPowerMin OBJECT-TYPE
    SYNTAX      DisplayString (SIZE (0..255))
    MAX-ACCESS  read-only
    STATUS      deprecated
    DESCRIPTION
            "the interface min tx power."
    ::= { slot7ModuleIfEntry 36 }  

slot7ModuleifTxPowerMax OBJECT-TYPE
    SYNTAX      DisplayString (SIZE (0..255))
    MAX-ACCESS  read-only
    STATUS      deprecated
    DESCRIPTION
            "the interface max tx power."
    ::= { slot7ModuleIfEntry 37 }  

slot7ModuleifRxHisPeak OBJECT-TYPE
    SYNTAX      Counter64
    MAX-ACCESS  read-only
    STATUS      current
    DESCRIPTION
            "The max speed of rx rate on the interface(kbps)"
    ::= { slot7ModuleIfEntry 38 }

slot7ModuleifTxHisPeak OBJECT-TYPE
    SYNTAX      Counter64
    MAX-ACCESS  read-only
    STATUS      current
    DESCRIPTION
            "The max speed of tx rate on the interface(kbps)"
    ::= { slot7ModuleIfEntry 39 }

slot7ModuleifMode OBJECT-TYPE
    SYNTAX      DisplayString (SIZE (0..255))
    MAX-ACCESS  read-only
    STATUS      deprecated
    DESCRIPTION
            "the interface if mode."
    ::= { slot7ModuleIfEntry 40 }  

-- slot 8 --

-- slot8Table --

slot8Table OBJECT-TYPE
    SYNTAX      SEQUENCE OF Slot8Entry
    MAX-ACCESS  not-accessible
    STATUS      current
    DESCRIPTION
            "A list of all slot8Type's utilization."
    ::= { slot8 1 }  

slot8Entry OBJECT-TYPE
    SYNTAX      Slot8Entry
    MAX-ACCESS  not-accessible
    STATUS      current
    DESCRIPTION
            "An entry contains a slot8's utilization."
    INDEX   { slot8Index }
    ::= { slot8Table 1 }

Slot8Entry ::=
    SEQUENCE {     
		slot8Index                       Integer32,
		slot8Type                        DisplayString,
		slot8Status                      DisplayString,		
        slot8SerialNumber                DisplayString,		
        slot8Temperature                 DisplayString
    }  

slot8Index OBJECT-TYPE
    SYNTAX      Integer32 (1..2147483647)
    MAX-ACCESS  not-accessible
    STATUS      current
    DESCRIPTION
            "A unique value, greater than zero, for each chassis`s slot8."
    ::= { slot8Entry 1 }

slot8Type OBJECT-TYPE
    SYNTAX      DisplayString (SIZE (0..255))
    MAX-ACCESS  read-only
    STATUS      current
    DESCRIPTION
            "the slot8Type of each chassis."
    ::= { slot8Entry 2 }

slot8Status OBJECT-TYPE
    SYNTAX      DisplayString (SIZE (0..255))
    MAX-ACCESS  read-only
    STATUS      current
    DESCRIPTION
            "A string to describe the board status." 
    ::= { slot8Entry 3 }   


slot8SerialNumber OBJECT-TYPE
    SYNTAX      DisplayString (SIZE (0..255))
    MAX-ACCESS  read-only
    STATUS      current
    DESCRIPTION
            "A string to describe the board serial number." 
    ::= { slot8Entry 4 }   

slot8Temperature OBJECT-TYPE
    SYNTAX      DisplayString (SIZE (0..255))
    MAX-ACCESS  read-only
    STATUS      current
    DESCRIPTION
            "A string to describe the board temperature." 
    ::= { slot8Entry 5 }   


slot8Module OBJECT IDENTIFIER ::= { slot8 2 }

-- slot8ModuleTable --
slot8ModuleTable OBJECT-TYPE
    SYNTAX      SEQUENCE OF Slot8ModuleEntry
    MAX-ACCESS  not-accessible
    STATUS      current
    DESCRIPTION
            "A list of all slot8Module's utilization."
    ::= { slot8Module 1 }  

slot8ModuleEntry OBJECT-TYPE
    SYNTAX      Slot8ModuleEntry
    MAX-ACCESS  not-accessible
    STATUS      current
    DESCRIPTION
            "An entry contains a slot8Module's utilization."
    INDEX   { slot8ModuleIndex }
    ::= { slot8ModuleTable 1 }

Slot8ModuleEntry ::=
    SEQUENCE {     
		slot8ModuleIndex                       Integer32,
		slot8ModuleId                           DisplayString,  
		slot8ModuleIfNumber                     Integer32		
    } 

slot8ModuleIndex OBJECT-TYPE
    SYNTAX      Integer32 (1..2147483647)
    MAX-ACCESS  not-accessible
    STATUS      current
    DESCRIPTION
            "A unique value, greater than zero, for each chassis`s slot8."
    ::= { slot8ModuleEntry 1 }

slot8ModuleId OBJECT-TYPE
    SYNTAX      DisplayString (SIZE (0..32))
    MAX-ACCESS  read-only
    STATUS      current
    DESCRIPTION
            "the value of module`s id"
    ::= { slot8ModuleEntry 2 }
  
slot8ModuleIfNumber OBJECT-TYPE
    SYNTAX      Integer32(0..2147483647)
    MAX-ACCESS  read-only
    STATUS      current
    DESCRIPTION
            "The number of network interfaces (regardless of their
            current state) present on this system." 
    ::= { slot8ModuleEntry 3 } 
    
slot8ModuleIfTable OBJECT-TYPE
    SYNTAX      SEQUENCE OF Slot8ModuleIfEntry
    MAX-ACCESS  not-accessible
    STATUS      current
    DESCRIPTION
            "A list of interface entries.  The number of entries is
            given by the value of ifNumber."
    ::= { slot8Module 2 } 
    
slot8ModuleIfEntry OBJECT-TYPE
    SYNTAX      Slot8ModuleIfEntry
    MAX-ACCESS  not-accessible
    STATUS      current
    DESCRIPTION
            "An entry containing management information applicable to a
            particular interface."
    INDEX   { slot8ModuleifIndex }
    ::= { slot8ModuleIfTable 1 }
    
Slot8ModuleIfEntry ::=
    SEQUENCE {
        slot8ModuleifIndex                 InterfaceIndex,  
        slot8ModuleIfId                    DisplayString,  
        slot8ModuleifDescr                 DisplayString,           
        slot8ModuleifType                  IANAifType,   		
        slot8ModuleifMtu                   Integer32,                
        slot8ModuleifSpeed                 Counter64,               
        slot8ModuleifPhysAddress           PhysAddress,              
        slot8ModuleifAdminStatus           INTEGER,                  
        slot8ModuleifOperStatus            INTEGER,                  
        slot8ModuleifLastChange            TimeTicks,                
        slot8ModuleifInOctets              Counter64,                
        slot8ModuleifInUcastPkts           Counter64,                
        slot8ModuleifInNUcastPkts          Counter64,  
        slot8ModuleifInDiscards            Counter64,
        slot8ModuleifInErrors              Counter64,
        slot8ModuleifInFcsErrorPkts        Counter64,
        slot8ModuleifInUnknownProtos       Counter64,	-- deprecated
        slot8ModuleifOutOctets             Counter64,
        slot8ModuleifOutUcastPkts          Counter64,
        slot8ModuleifOutNUcastPkts         Counter64,  -- deprecated
        slot8ModuleifOutDiscards           Counter64,
        slot8ModuleifOutErrors             Counter64,
        slot8ModuleifOutFcsErrorPkts       Counter64,
        slot8ModuleifOutQLen               Gauge32,    -- deprecated  
        slot8ModuleifOutOctetsRate         Counter64,
        slot8ModuleifInOctetsRate          Counter64,
        slot8ModuleifOutPktsRate           Counter64,
        slot8ModuleifInPktsRate            Counter64,
        slot8ModuleifRxPower               DisplayString,
        slot8ModuleifTxPower               DisplayString,
        slot8ModuleifSpecific              OBJECT IDENTIFIER,
        slot8ModuleifTxMirrorList          DisplayString,
        slot8ModuleifRxMirrorList          DisplayString,
        slot8ModuleifRxPowerMin               DisplayString,
        slot8ModuleifRxPowerMax               DisplayString,
        slot8ModuleifTxPowerMin               DisplayString,
        slot8ModuleifTxPowerMax               DisplayString,
        slot8ModuleifRxHisPeak            Counter64,
        slot8ModuleifTxHisPeak            Counter64,
        slot8ModuleifMode                 DisplayString   		
    }         

slot8ModuleifIndex OBJECT-TYPE
    SYNTAX      InterfaceIndex
    MAX-ACCESS  read-only
    STATUS      current
    DESCRIPTION
            "A unique value, greater than zero, for each interface.  It
            is recommended that values are assigned contiguously
            starting from 1.  The value for each interface sub-layer
            must remain constant at least from one re-initialization of
            the entity's network management system to the next re-
            initialization."
    ::= { slot8ModuleIfEntry 1 }
    
slot8ModuleIfId OBJECT-TYPE
    SYNTAX      DisplayString (SIZE (0..32))
    MAX-ACCESS  read-only
    STATUS      current
    DESCRIPTION
            "the value of module`s id"
    ::= { slot8ModuleIfEntry 2 }
    
slot8ModuleifDescr OBJECT-TYPE
    SYNTAX      DisplayString (SIZE (0..255))
    MAX-ACCESS  read-only
    STATUS      current
    DESCRIPTION
            "A textual string containing information about the
            interface.  This string should include the name of the
            manufacturer, the product name and the version of the
            interface hardware/software."
    ::= { slot8ModuleIfEntry 3 }
    
slot8ModuleifType OBJECT-TYPE
    SYNTAX      IANAifType
    MAX-ACCESS  read-only
    STATUS      current
    DESCRIPTION
            "The type of interface.  Additional values for ifType are
            assigned by the Internet Assigned Numbers Authority (IANA),
            through updating the syntax of the IANAifType textual
            convention."
    ::= { slot8ModuleIfEntry 4 }

slot8ModuleifMtu OBJECT-TYPE
    SYNTAX      Integer32(1..2147483647)
    MAX-ACCESS  read-only
    STATUS      current
    DESCRIPTION
            "The size of the largest packet which can be sent/received
            on the interface, specified in octets.  For interfaces that
            are used for transmitting network datagrams, this is the
            size of the largest network datagram that can be sent on the
            interface."
    ::= { slot8ModuleIfEntry 5 }

slot8ModuleifSpeed OBJECT-TYPE
    SYNTAX      Counter64
    MAX-ACCESS  read-only
    STATUS      current
    DESCRIPTION
            "An estimate of the interface's current bandwidth in bits
            per second.  For interfaces which do not vary in bandwidth
            or for those where no accurate estimation can be made, this
            object should contain the nominal bandwidth. For a sub-layer
            which has no concept of bandwidth, this object should be zero."
    ::= { slot8ModuleIfEntry 6 }

slot8ModuleifPhysAddress OBJECT-TYPE
    SYNTAX      PhysAddress
    MAX-ACCESS  read-only
    STATUS      current
    DESCRIPTION
            "The interface's address at its protocol sub-layer.  For
            example, for an 802.x interface, this object normally
            contains a MAC address.  The interface's media-specific MIB
            must define the bit and byte ordering and the format of the
            value of this object.  For interfaces which do not have such
            an address (e.g., a serial line), this object should contain
            an octet string of zero length."
    ::= { slot8ModuleIfEntry 7 }
    
slot8ModuleifAdminStatus OBJECT-TYPE
    SYNTAX  INTEGER {
                up(1),       -- ready to pass packets
                down(2),
                testing(3)   -- in some test mode
            }
    MAX-ACCESS  read-write
    STATUS      current
    DESCRIPTION
            "The desired state of the interface.  The testing(3) state
            indicates that no operational packets can be passed.  When a
            managed system initializes, all interfaces start with
            ifAdminStatus in the down(2) state.  As a result of either
            explicit management action or per configuration information
            retained by the managed system, ifAdminStatus is then
            changed to either the up(1) or testing(3) states (or remains
            in the down(2) state)."
    ::= { slot8ModuleIfEntry 8 }

slot8ModuleifOperStatus OBJECT-TYPE
    SYNTAX  INTEGER {
                up(1),        -- ready to pass packets
                down(2),
                testing(3),   -- in some test mode
                unknown(4),   -- status can not be determined
                              -- for some reason.
                dormant(5),
                notPresent(6),    -- some component is missing
                lowerLayerDown(7) -- down due to state of
                                  -- lower-layer interface(s)
            }
    MAX-ACCESS  read-only
    STATUS      current
    DESCRIPTION
            "The current operational state of the interface.  The
            testing(3) state indicates that no operational packets can
            be passed.  If ifAdminStatus is down(2) then ifOperStatus
            should be down(2).  If ifAdminStatus is changed to up(1)
            then ifOperStatus should change to up(1) if the interface is
            ready to transmit and receive network traffic; it should
            change to dormant(5) if the interface is waiting for
            external actions (such as a serial line waiting for an
            incoming connection); it should remain in the down(2) state
            if and only if there is a fault that prevents it from going
            to the up(1) state; it should remain in the notPresent(6)
            state if the interface has missing (typically, hardware)
            components."
    ::= { slot8ModuleIfEntry 9 }

slot8ModuleifLastChange OBJECT-TYPE
    SYNTAX      TimeTicks
    MAX-ACCESS  read-only
    STATUS      current
    DESCRIPTION
            "The value of sysUpTime at the time the interface entered
            its current operational state.  If the current state was
            entered prior to the last re-initialization of the local
            network management subsystem, then this object contains a
            zero value."
    ::= { slot8ModuleIfEntry 10 }

slot8ModuleifInOctets OBJECT-TYPE
    SYNTAX      Counter64
    MAX-ACCESS  read-only
    STATUS      current
    DESCRIPTION
            "The total number of octets received on the interface,
            including framing characters.

            Discontinuities in the value of this counter can occur at
            re-initialization of the management system, and at other
            times as indicated by the value of
            ifCounterDiscontinuityTime."
    ::= { slot8ModuleIfEntry 11 }

slot8ModuleifInUcastPkts OBJECT-TYPE
    SYNTAX      Counter64
    MAX-ACCESS  read-only
    STATUS      current
    DESCRIPTION
            "The number of packets, delivered by this sub-layer to a
            higher (sub-)layer, which were not addressed to a multicast
            or broadcast address at this sub-layer.

            Discontinuities in the value of this counter can occur at
            re-initialization of the management system, and at other
            times as indicated by the value of
            ifCounterDiscontinuityTime."
    ::= { slot8ModuleIfEntry 12 }

slot8ModuleifInNUcastPkts OBJECT-TYPE
    SYNTAX  Counter64
    MAX-ACCESS  read-only
    STATUS      current
    DESCRIPTION
            "The number of packets, delivered by this sub-layer to a
            higher (sub-)layer, which were addressed to a multicast or
            broadcast address at this sub-layer.

            Discontinuities in the value of this counter can occur at
            re-initialization of the management system, and at other
            times as indicated by the value of
            ifCounterDiscontinuityTime.

            This object is deprecated in favour of ifInMulticastPkts and
            ifInBroadcastPkts."
    ::= { slot8ModuleIfEntry 13 }

slot8ModuleifInDiscards OBJECT-TYPE
    SYNTAX      Counter64
    MAX-ACCESS  read-only
    STATUS      current
    DESCRIPTION
            "The number of inbound packets which were chosen to be
            discarded even though no errors had been detected to prevent

            their being deliverable to a higher-layer protocol.  One
            possible reason for discarding such a packet could be to
            free up buffer space.

            Discontinuities in the value of this counter can occur at
            re-initialization of the management system, and at other
            times as indicated by the value of
            ifCounterDiscontinuityTime."
    ::= { slot8ModuleIfEntry 14 }

slot8ModuleifInErrors OBJECT-TYPE
    SYNTAX      Counter64
    MAX-ACCESS  read-only
    STATUS      current
    DESCRIPTION
            "For packet-oriented interfaces, the number of inbound
            packets that contained errors preventing them from being
            deliverable to a higher-layer protocol.  For character-
            oriented or fixed-length interfaces, the number of inbound
            transmission units that contained errors preventing them
            from being deliverable to a higher-layer protocol.

            Discontinuities in the value of this counter can occur at
            re-initialization of the management system, and at other
            times as indicated by the value of
            ifCounterDiscontinuityTime."
    ::= { slot8ModuleIfEntry 15 }

slot8ModuleifInFcsErrorPkts OBJECT-TYPE
    SYNTAX      Counter64
    MAX-ACCESS  read-only
    STATUS      current
    DESCRIPTION
            "FCS error pakets."
    ::= { slot8ModuleIfEntry 16 }

slot8ModuleifInUnknownProtos OBJECT-TYPE
    SYNTAX      Counter64
    MAX-ACCESS  read-only
    STATUS      current
    DESCRIPTION
            "For packet-oriented interfaces, the number of packets
            received via the interface which were discarded because of
            an unknown or unsupported protocol.  For character-oriented
            or fixed-length interfaces that support protocol
            multiplexing the number of transmission units received via
            the interface which were discarded because of an unknown or
            unsupported protocol.  For any interface that does not
            support protocol multiplexing, this counter will always be
            0.

            Discontinuities in the value of this counter can occur at
            re-initialization of the management system, and at other
            times as indicated by the value of
            ifCounterDiscontinuityTime."
    ::= { slot8ModuleIfEntry 17 }

slot8ModuleifOutOctets OBJECT-TYPE
    SYNTAX      Counter64
    MAX-ACCESS  read-only
    STATUS      current
    DESCRIPTION
            "The total number of octets transmitted out of the
            interface, including framing characters.

            Discontinuities in the value of this counter can occur at
            re-initialization of the management system, and at other
            times as indicated by the value of
            ifCounterDiscontinuityTime."
    ::= { slot8ModuleIfEntry 18 }

slot8ModuleifOutUcastPkts OBJECT-TYPE
    SYNTAX      Counter64
    MAX-ACCESS  read-only
    STATUS      current
    DESCRIPTION
            "The total number of packets that higher-level protocols
            requested be transmitted, and which were not addressed to a
            multicast or broadcast address at this sub-layer, including
            those that were discarded or not sent.

            Discontinuities in the value of this counter can occur at
            re-initialization of the management system, and at other
            times as indicated by the value of
            ifCounterDiscontinuityTime."
    ::= { slot8ModuleIfEntry 19 }

slot8ModuleifOutNUcastPkts OBJECT-TYPE
    SYNTAX      Counter64
    MAX-ACCESS  read-only
    STATUS      deprecated
    DESCRIPTION
            "The total number of packets that higher-level protocols
            requested be transmitted, and which were addressed to a
            multicast or broadcast address at this sub-layer, including
            those that were discarded or not sent.

            Discontinuities in the value of this counter can occur at
            re-initialization of the management system, and at other
            times as indicated by the value of
            ifCounterDiscontinuityTime.

            This object is deprecated in favour of ifOutMulticastPkts
            and ifOutBroadcastPkts."
    ::= { slot8ModuleIfEntry 20 }

slot8ModuleifOutDiscards OBJECT-TYPE
    SYNTAX      Counter64
    MAX-ACCESS  read-only
    STATUS      current
    DESCRIPTION
            "The number of outbound packets which were chosen to be
            discarded even though no errors had been detected to prevent
            their being transmitted.  One possible reason for discarding
            such a packet could be to free up buffer space.

            Discontinuities in the value of this counter can occur at
            re-initialization of the management system, and at other
            times as indicated by the value of
            ifCounterDiscontinuityTime."
    ::= { slot8ModuleIfEntry 21 }

slot8ModuleifOutErrors OBJECT-TYPE
    SYNTAX      Counter64
    MAX-ACCESS  read-only
    STATUS      current
    DESCRIPTION
            "For packet-oriented interfaces, the number of outbound
            packets that could not be transmitted because of errors.
            For character-oriented or fixed-length interfaces, the
            number of outbound transmission units that could not be
            transmitted because of errors.

            Discontinuities in the value of this counter can occur at
            re-initialization of the management system, and at other
            times as indicated by the value of
            ifCounterDiscontinuityTime."
    ::= { slot8ModuleIfEntry 22 }

slot8ModuleifOutFcsErrorPkts OBJECT-TYPE
    SYNTAX      Counter64
    MAX-ACCESS  read-only
    STATUS      current
    DESCRIPTION
            "FCS error pakets."
    ::= { slot8ModuleIfEntry 23 }

slot8ModuleifOutQLen OBJECT-TYPE
    SYNTAX      Gauge32
    MAX-ACCESS  read-only
    STATUS      deprecated
    DESCRIPTION
            "The length of the output packet queue (in packets)."
    ::= { slot8ModuleIfEntry 24 }

slot8ModuleifOutOctetsRate OBJECT-TYPE
    SYNTAX      Counter64
    MAX-ACCESS  read-only
    STATUS      current
    DESCRIPTION
            "The speed of octets trans on the interface(kbps)"
    ::= { slot8ModuleIfEntry 25 }

slot8ModuleifInOctetsRate OBJECT-TYPE
    SYNTAX      Counter64
    MAX-ACCESS  read-only
    STATUS      current
    DESCRIPTION
            "The speed of octets received on the interface(kbps)"
    ::= { slot8ModuleIfEntry 26 }

slot8ModuleifOutPktsRate OBJECT-TYPE
    SYNTAX      Counter64
    MAX-ACCESS  read-only
    STATUS      current
    DESCRIPTION
            "The speed of packets trans on the interface(pps)"
    ::= { slot8ModuleIfEntry 27 }

slot8ModuleifInPktsRate OBJECT-TYPE
    SYNTAX      Counter64
    MAX-ACCESS  read-only
    STATUS      current
    DESCRIPTION
            "The speed of octets received on the interface(kbps)"
    ::= { slot8ModuleIfEntry 28 }

slot8ModuleifRxPower OBJECT-TYPE
    SYNTAX      DisplayString (SIZE (0..255))
    MAX-ACCESS  read-only
    STATUS      current
    DESCRIPTION
            "the value of interface's received power, in dbm format."
    ::= { slot8ModuleIfEntry 29 }

slot8ModuleifTxPower OBJECT-TYPE
    SYNTAX      DisplayString (SIZE (0..255))
    MAX-ACCESS  read-only
    STATUS      current
    DESCRIPTION
            "the value of interface's send power, in dbm format."
    ::= { slot8ModuleIfEntry 30 }

slot8ModuleifSpecific OBJECT-TYPE
    SYNTAX      OBJECT IDENTIFIER
    MAX-ACCESS  read-only
    STATUS      deprecated
    DESCRIPTION
            "A reference to MIB definitions specific to the particular
            media being used to realize the interface.  It is

            recommended that this value point to an instance of a MIB
            object in the media-specific MIB, i.e., that this object
            have the semantics associated with the InstancePointer
            textual convention defined in RFC 2579.  In fact, it is
            recommended that the media-specific MIB specify what value
            ifSpecific should/can take for values of ifType.  If no MIB
            definitions specific to the particular media are available,
            the value should be set to the OBJECT IDENTIFIER { 0 0 }."
    ::= { slot8ModuleIfEntry 31 }  
   
slot8ModuleifTxMirrorList OBJECT-TYPE
    SYNTAX      DisplayString (SIZE (0..255))
    MAX-ACCESS  read-only
    STATUS      deprecated
    DESCRIPTION
            "the interface tx mirror list."
    ::= { slot8ModuleIfEntry 32 }  
 
slot8ModuleifRxMirrorList OBJECT-TYPE
    SYNTAX      DisplayString (SIZE (0..255))
    MAX-ACCESS  read-only
    STATUS      deprecated
    DESCRIPTION
            "the interface rx mirror list."
    ::= { slot8ModuleIfEntry 33 }  
  
slot8ModuleifRxPowerMin OBJECT-TYPE
    SYNTAX      DisplayString (SIZE (0..255))
    MAX-ACCESS  read-only
    STATUS      deprecated
    DESCRIPTION
            "the interface min rx power."
    ::= { slot8ModuleIfEntry 34 }  

slot8ModuleifRxPowerMax OBJECT-TYPE
    SYNTAX      DisplayString (SIZE (0..255))
    MAX-ACCESS  read-only
    STATUS      deprecated
    DESCRIPTION
            "the interface max rx power."
    ::= { slot8ModuleIfEntry 35 }  

slot8ModuleifTxPowerMin OBJECT-TYPE
    SYNTAX      DisplayString (SIZE (0..255))
    MAX-ACCESS  read-only
    STATUS      deprecated
    DESCRIPTION
            "the interface min tx power."
    ::= { slot8ModuleIfEntry 36 }  

slot8ModuleifTxPowerMax OBJECT-TYPE
    SYNTAX      DisplayString (SIZE (0..255))
    MAX-ACCESS  read-only
    STATUS      deprecated
    DESCRIPTION
            "the interface max tx power."
    ::= { slot8ModuleIfEntry 37 }  

 slot8ModuleifRxHisPeak OBJECT-TYPE
    SYNTAX      Counter64
    MAX-ACCESS  read-only
    STATUS      current
    DESCRIPTION
            "The max speed of rx rate on the interface(kbps)"
    ::= { slot8ModuleIfEntry 38 }

slot8ModuleifTxHisPeak OBJECT-TYPE
    SYNTAX      Counter64
    MAX-ACCESS  read-only
    STATUS      current
    DESCRIPTION
            "The max speed of tx rate on the interface(kbps)"
    ::= { slot8ModuleIfEntry 39 }

slot8ModuleifMode OBJECT-TYPE
    SYNTAX      DisplayString (SIZE (0..255))
    MAX-ACCESS  read-only
    STATUS      deprecated
    DESCRIPTION
            "the interface if mode."
    ::= { slot8ModuleIfEntry 40 }  

-- slot 9 --

-- slot9Table --

slot9Table OBJECT-TYPE
    SYNTAX      SEQUENCE OF Slot9Entry
    MAX-ACCESS  not-accessible
    STATUS      current
    DESCRIPTION
            "A list of all slot9Type's utilization."
    ::= { slot9 1 }  

slot9Entry OBJECT-TYPE
    SYNTAX      Slot9Entry
    MAX-ACCESS  not-accessible
    STATUS      current
    DESCRIPTION
            "An entry contains a slot9's utilization."
    INDEX   { slot9Index }
    ::= { slot9Table 1 }

Slot9Entry ::=
    SEQUENCE {     
		slot9Index                       Integer32,
		slot9Type                        DisplayString,
		slot9Status                      DisplayString,		
        slot9SerialNumber                DisplayString,		
        slot9Temperature                 DisplayString
    }  

slot9Index OBJECT-TYPE
    SYNTAX      Integer32 (1..2147483647)
    MAX-ACCESS  not-accessible
    STATUS      current
    DESCRIPTION
            "A unique value, greater than zero, for each chassis`s slot9."
    ::= { slot9Entry 1 }

slot9Type OBJECT-TYPE
    SYNTAX      DisplayString (SIZE (0..255))
    MAX-ACCESS  read-only
    STATUS      current
    DESCRIPTION
            "the slot9Type of each chassis."
    ::= { slot9Entry 2 }

slot9Status OBJECT-TYPE
    SYNTAX      DisplayString (SIZE (0..255))
    MAX-ACCESS  read-only
    STATUS      current
    DESCRIPTION
            "A string to describe the board status." 
    ::= { slot9Entry 3 }   


slot9SerialNumber OBJECT-TYPE
    SYNTAX      DisplayString (SIZE (0..255))
    MAX-ACCESS  read-only
    STATUS      current
    DESCRIPTION
            "A string to describe the board serial number." 
    ::= { slot9Entry 4 }   

slot9Temperature OBJECT-TYPE
    SYNTAX      DisplayString (SIZE (0..255))
    MAX-ACCESS  read-only
    STATUS      current
    DESCRIPTION
            "A string to describe the board temperature." 
    ::= { slot9Entry 5 }   


slot9Module OBJECT IDENTIFIER ::= { slot9 2 }

-- slot9ModuleTable --
slot9ModuleTable OBJECT-TYPE
    SYNTAX      SEQUENCE OF Slot9ModuleEntry
    MAX-ACCESS  not-accessible
    STATUS      current
    DESCRIPTION
            "A list of all slot9Module's utilization."
    ::= { slot9Module 1 }  

slot9ModuleEntry OBJECT-TYPE
    SYNTAX      Slot9ModuleEntry
    MAX-ACCESS  not-accessible
    STATUS      current
    DESCRIPTION
            "An entry contains a slot9Module's utilization."
    INDEX   { slot9ModuleIndex }
    ::= { slot9ModuleTable 1 }

Slot9ModuleEntry ::=
    SEQUENCE {     
		slot9ModuleIndex                       Integer32,
		slot9ModuleId                           DisplayString,  
		slot9ModuleIfNumber                     Integer32		
    } 

slot9ModuleIndex OBJECT-TYPE
    SYNTAX      Integer32 (1..2147483647)
    MAX-ACCESS  not-accessible
    STATUS      current
    DESCRIPTION
            "A unique value, greater than zero, for each chassis`s slot9."
    ::= { slot9ModuleEntry 1 }

slot9ModuleId OBJECT-TYPE
    SYNTAX      DisplayString (SIZE (0..32))
    MAX-ACCESS  read-only
    STATUS      current
    DESCRIPTION
            "the value of module`s id"
    ::= { slot9ModuleEntry 2 }
  
slot9ModuleIfNumber OBJECT-TYPE
    SYNTAX      Integer32(0..2147483647)
    MAX-ACCESS  read-only
    STATUS      current
    DESCRIPTION
            "The number of network interfaces (regardless of their
            current state) present on this system." 
    ::= { slot9ModuleEntry 3 } 
    
slot9ModuleIfTable OBJECT-TYPE
    SYNTAX      SEQUENCE OF Slot9ModuleIfEntry
    MAX-ACCESS  not-accessible
    STATUS      current
    DESCRIPTION
            "A list of interface entries.  The number of entries is
            given by the value of ifNumber."
    ::= { slot9Module 2 } 
    
slot9ModuleIfEntry OBJECT-TYPE
    SYNTAX      Slot9ModuleIfEntry
    MAX-ACCESS  not-accessible
    STATUS      current
    DESCRIPTION
            "An entry containing management information applicable to a
            particular interface."
    INDEX   { slot9ModuleifIndex }
    ::= { slot9ModuleIfTable 1 }
    
Slot9ModuleIfEntry ::=
    SEQUENCE {
        slot9ModuleifIndex                 InterfaceIndex,  
        slot9ModuleIfId                    DisplayString,  
        slot9ModuleifDescr                 DisplayString,           
        slot9ModuleifType                  IANAifType,   		
        slot9ModuleifMtu                   Integer32,                
        slot9ModuleifSpeed                 Counter64,               
        slot9ModuleifPhysAddress           PhysAddress,              
        slot9ModuleifAdminStatus           INTEGER,                  
        slot9ModuleifOperStatus            INTEGER,                  
        slot9ModuleifLastChange            TimeTicks,                
        slot9ModuleifInOctets              Counter64,                
        slot9ModuleifInUcastPkts           Counter64,                
        slot9ModuleifInNUcastPkts          Counter64,   
        slot9ModuleifInDiscards            Counter64,
        slot9ModuleifInErrors              Counter64,
        slot9ModuleifInFcsErrorPkts        Counter64,
        slot9ModuleifInUnknownProtos       Counter64,	-- deprecated
        slot9ModuleifOutOctets             Counter64,
        slot9ModuleifOutUcastPkts          Counter64,
        slot9ModuleifOutNUcastPkts         Counter64,  -- deprecated
        slot9ModuleifOutDiscards           Counter64,
        slot9ModuleifOutErrors             Counter64,
        slot9ModuleifOutFcsErrorPkts       Counter64,
        slot9ModuleifOutQLen               Gauge32,    -- deprecated  
        slot9ModuleifOutOctetsRate         Counter64,
        slot9ModuleifInOctetsRate          Counter64,
        slot9ModuleifOutPktsRate           Counter64,
        slot9ModuleifInPktsRate            Counter64,
        slot9ModuleifRxPower               DisplayString,
        slot9ModuleifTxPower               DisplayString,
        slot9ModuleifSpecific              OBJECT IDENTIFIER,
        slot9ModuleifTxMirrorList          DisplayString,
        slot9ModuleifRxMirrorList          DisplayString,
        slot9ModuleifRxPowerMin               DisplayString,
        slot9ModuleifRxPowerMax               DisplayString,
        slot9ModuleifTxPowerMin               DisplayString,
        slot9ModuleifTxPowerMax               DisplayString,
        slot9ModuleifRxHisPeak            Counter64,
        slot9ModuleifTxHisPeak            Counter64,
        slot9ModuleifMode                 DisplayString   		
    }         

slot9ModuleifIndex OBJECT-TYPE
    SYNTAX      InterfaceIndex
    MAX-ACCESS  read-only
    STATUS      current
    DESCRIPTION
            "A unique value, greater than zero, for each interface.  It
            is recommended that values are assigned contiguously
            starting from 1.  The value for each interface sub-layer
            must remain constant at least from one re-initialization of
            the entity's network management system to the next re-
            initialization."
    ::= { slot9ModuleIfEntry 1 }
    
slot9ModuleIfId OBJECT-TYPE
    SYNTAX      DisplayString (SIZE (0..32))
    MAX-ACCESS  read-only
    STATUS      current
    DESCRIPTION
            "the value of module`s id"
    ::= { slot9ModuleIfEntry 2 }
    
slot9ModuleifDescr OBJECT-TYPE
    SYNTAX      DisplayString (SIZE (0..255))
    MAX-ACCESS  read-only
    STATUS      current
    DESCRIPTION
            "A textual string containing information about the
            interface.  This string should include the name of the
            manufacturer, the product name and the version of the
            interface hardware/software."
    ::= { slot9ModuleIfEntry 3 }
    
slot9ModuleifType OBJECT-TYPE
    SYNTAX      IANAifType
    MAX-ACCESS  read-only
    STATUS      current
    DESCRIPTION
            "The type of interface.  Additional values for ifType are
            assigned by the Internet Assigned Numbers Authority (IANA),
            through updating the syntax of the IANAifType textual
            convention."
    ::= { slot9ModuleIfEntry 4 }

slot9ModuleifMtu OBJECT-TYPE
    SYNTAX      Integer32(1..2147483647)
    MAX-ACCESS  read-only
    STATUS      current
    DESCRIPTION
            "The size of the largest packet which can be sent/received
            on the interface, specified in octets.  For interfaces that
            are used for transmitting network datagrams, this is the
            size of the largest network datagram that can be sent on the
            interface."
    ::= { slot9ModuleIfEntry 5 }

slot9ModuleifSpeed OBJECT-TYPE
    SYNTAX      Counter64
    MAX-ACCESS  read-only
    STATUS      current
    DESCRIPTION
            "An estimate of the interface's current bandwidth in bits
            per second.  For interfaces which do not vary in bandwidth
            or for those where no accurate estimation can be made, this
            object should contain the nominal bandwidth. For a sub-layer
            which has no concept of bandwidth, this object should be zero."
    ::= { slot9ModuleIfEntry 6 }

slot9ModuleifPhysAddress OBJECT-TYPE
    SYNTAX      PhysAddress
    MAX-ACCESS  read-only
    STATUS      current
    DESCRIPTION
            "The interface's address at its protocol sub-layer.  For
            example, for an 802.x interface, this object normally
            contains a MAC address.  The interface's media-specific MIB
            must define the bit and byte ordering and the format of the
            value of this object.  For interfaces which do not have such
            an address (e.g., a serial line), this object should contain
            an octet string of zero length."
    ::= { slot9ModuleIfEntry 7 }
    
slot9ModuleifAdminStatus OBJECT-TYPE
    SYNTAX  INTEGER {
                up(1),       -- ready to pass packets
                down(2),
                testing(3)   -- in some test mode
            }
    MAX-ACCESS  read-write
    STATUS      current
    DESCRIPTION
            "The desired state of the interface.  The testing(3) state
            indicates that no operational packets can be passed.  When a
            managed system initializes, all interfaces start with
            ifAdminStatus in the down(2) state.  As a result of either
            explicit management action or per configuration information
            retained by the managed system, ifAdminStatus is then
            changed to either the up(1) or testing(3) states (or remains
            in the down(2) state)."
    ::= { slot9ModuleIfEntry 8 }

slot9ModuleifOperStatus OBJECT-TYPE
    SYNTAX  INTEGER {
                up(1),        -- ready to pass packets
                down(2),
                testing(3),   -- in some test mode
                unknown(4),   -- status can not be determined
                              -- for some reason.
                dormant(5),
                notPresent(6),    -- some component is missing
                lowerLayerDown(7) -- down due to state of
                                  -- lower-layer interface(s)
            }
    MAX-ACCESS  read-only
    STATUS      current
    DESCRIPTION
            "The current operational state of the interface.  The
            testing(3) state indicates that no operational packets can
            be passed.  If ifAdminStatus is down(2) then ifOperStatus
            should be down(2).  If ifAdminStatus is changed to up(1)
            then ifOperStatus should change to up(1) if the interface is
            ready to transmit and receive network traffic; it should
            change to dormant(5) if the interface is waiting for
            external actions (such as a serial line waiting for an
            incoming connection); it should remain in the down(2) state
            if and only if there is a fault that prevents it from going
            to the up(1) state; it should remain in the notPresent(6)
            state if the interface has missing (typically, hardware)
            components."
    ::= { slot9ModuleIfEntry 9 }

slot9ModuleifLastChange OBJECT-TYPE
    SYNTAX      TimeTicks
    MAX-ACCESS  read-only
    STATUS      current
    DESCRIPTION
            "The value of sysUpTime at the time the interface entered
            its current operational state.  If the current state was
            entered prior to the last re-initialization of the local
            network management subsystem, then this object contains a
            zero value."
    ::= { slot9ModuleIfEntry 10 }

slot9ModuleifInOctets OBJECT-TYPE
    SYNTAX      Counter64
    MAX-ACCESS  read-only
    STATUS      current
    DESCRIPTION
            "The total number of octets received on the interface,
            including framing characters.

            Discontinuities in the value of this counter can occur at
            re-initialization of the management system, and at other
            times as indicated by the value of
            ifCounterDiscontinuityTime."
    ::= { slot9ModuleIfEntry 11 }

slot9ModuleifInUcastPkts OBJECT-TYPE
    SYNTAX      Counter64
    MAX-ACCESS  read-only
    STATUS      current
    DESCRIPTION
            "The number of packets, delivered by this sub-layer to a
            higher (sub-)layer, which were not addressed to a multicast
            or broadcast address at this sub-layer.

            Discontinuities in the value of this counter can occur at
            re-initialization of the management system, and at other
            times as indicated by the value of
            ifCounterDiscontinuityTime."
    ::= { slot9ModuleIfEntry 12 }

slot9ModuleifInNUcastPkts OBJECT-TYPE
    SYNTAX  Counter64
    MAX-ACCESS  read-only
    STATUS      current
    DESCRIPTION
            "The number of packets, delivered by this sub-layer to a
            higher (sub-)layer, which were addressed to a multicast or
            broadcast address at this sub-layer.

            Discontinuities in the value of this counter can occur at
            re-initialization of the management system, and at other
            times as indicated by the value of
            ifCounterDiscontinuityTime.

            This object is deprecated in favour of ifInMulticastPkts and
            ifInBroadcastPkts."
    ::= { slot9ModuleIfEntry 13 }

slot9ModuleifInDiscards OBJECT-TYPE
    SYNTAX      Counter64
    MAX-ACCESS  read-only
    STATUS      current
    DESCRIPTION
            "The number of inbound packets which were chosen to be
            discarded even though no errors had been detected to prevent

            their being deliverable to a higher-layer protocol.  One
            possible reason for discarding such a packet could be to
            free up buffer space.

            Discontinuities in the value of this counter can occur at
            re-initialization of the management system, and at other
            times as indicated by the value of
            ifCounterDiscontinuityTime."
    ::= { slot9ModuleIfEntry 14 }

slot9ModuleifInErrors OBJECT-TYPE
    SYNTAX      Counter64
    MAX-ACCESS  read-only
    STATUS      current
    DESCRIPTION
            "For packet-oriented interfaces, the number of inbound
            packets that contained errors preventing them from being
            deliverable to a higher-layer protocol.  For character-
            oriented or fixed-length interfaces, the number of inbound
            transmission units that contained errors preventing them
            from being deliverable to a higher-layer protocol.

            Discontinuities in the value of this counter can occur at
            re-initialization of the management system, and at other
            times as indicated by the value of
            ifCounterDiscontinuityTime."
    ::= { slot9ModuleIfEntry 15 }

slot9ModuleifInFcsErrorPkts OBJECT-TYPE
    SYNTAX      Counter64
    MAX-ACCESS  read-only
    STATUS      current
    DESCRIPTION
            "FCS error pakets."
    ::= { slot9ModuleIfEntry 16 }

slot9ModuleifInUnknownProtos OBJECT-TYPE
    SYNTAX      Counter64
    MAX-ACCESS  read-only
    STATUS      current
    DESCRIPTION
            "For packet-oriented interfaces, the number of packets
            received via the interface which were discarded because of
            an unknown or unsupported protocol.  For character-oriented
            or fixed-length interfaces that support protocol
            multiplexing the number of transmission units received via
            the interface which were discarded because of an unknown or
            unsupported protocol.  For any interface that does not
            support protocol multiplexing, this counter will always be
            0.

            Discontinuities in the value of this counter can occur at
            re-initialization of the management system, and at other
            times as indicated by the value of
            ifCounterDiscontinuityTime."
    ::= { slot9ModuleIfEntry 17 }

slot9ModuleifOutOctets OBJECT-TYPE
    SYNTAX      Counter64
    MAX-ACCESS  read-only
    STATUS      current
    DESCRIPTION
            "The total number of octets transmitted out of the
            interface, including framing characters.

            Discontinuities in the value of this counter can occur at
            re-initialization of the management system, and at other
            times as indicated by the value of
            ifCounterDiscontinuityTime."
    ::= { slot9ModuleIfEntry 18 }

slot9ModuleifOutUcastPkts OBJECT-TYPE
    SYNTAX      Counter64
    MAX-ACCESS  read-only
    STATUS      current
    DESCRIPTION
            "The total number of packets that higher-level protocols
            requested be transmitted, and which were not addressed to a
            multicast or broadcast address at this sub-layer, including
            those that were discarded or not sent.

            Discontinuities in the value of this counter can occur at
            re-initialization of the management system, and at other
            times as indicated by the value of
            ifCounterDiscontinuityTime."
    ::= { slot9ModuleIfEntry 19 }

slot9ModuleifOutNUcastPkts OBJECT-TYPE
    SYNTAX      Counter64
    MAX-ACCESS  read-only
    STATUS      deprecated
    DESCRIPTION
            "The total number of packets that higher-level protocols
            requested be transmitted, and which were addressed to a
            multicast or broadcast address at this sub-layer, including
            those that were discarded or not sent.

            Discontinuities in the value of this counter can occur at
            re-initialization of the management system, and at other
            times as indicated by the value of
            ifCounterDiscontinuityTime.

            This object is deprecated in favour of ifOutMulticastPkts
            and ifOutBroadcastPkts."
    ::= { slot9ModuleIfEntry 20 }

slot9ModuleifOutDiscards OBJECT-TYPE
    SYNTAX      Counter64
    MAX-ACCESS  read-only
    STATUS      current
    DESCRIPTION
            "The number of outbound packets which were chosen to be
            discarded even though no errors had been detected to prevent
            their being transmitted.  One possible reason for discarding
            such a packet could be to free up buffer space.

            Discontinuities in the value of this counter can occur at
            re-initialization of the management system, and at other
            times as indicated by the value of
            ifCounterDiscontinuityTime."
    ::= { slot9ModuleIfEntry 21 }

slot9ModuleifOutErrors OBJECT-TYPE
    SYNTAX      Counter64
    MAX-ACCESS  read-only
    STATUS      current
    DESCRIPTION
            "For packet-oriented interfaces, the number of outbound
            packets that could not be transmitted because of errors.
            For character-oriented or fixed-length interfaces, the
            number of outbound transmission units that could not be
            transmitted because of errors.

            Discontinuities in the value of this counter can occur at
            re-initialization of the management system, and at other
            times as indicated by the value of
            ifCounterDiscontinuityTime."
    ::= { slot9ModuleIfEntry 22 }

slot9ModuleifOutFcsErrorPkts OBJECT-TYPE
    SYNTAX      Counter64
    MAX-ACCESS  read-only
    STATUS      current
    DESCRIPTION
            "FCS error pakets."
    ::= { slot9ModuleIfEntry 23 }

slot9ModuleifOutQLen OBJECT-TYPE
    SYNTAX      Gauge32
    MAX-ACCESS  read-only
    STATUS      deprecated
    DESCRIPTION
            "The length of the output packet queue (in packets)."
    ::= { slot9ModuleIfEntry 24 }

slot9ModuleifOutOctetsRate OBJECT-TYPE
    SYNTAX      Counter64
    MAX-ACCESS  read-only
    STATUS      current
    DESCRIPTION
            "The speed of octets trans on the interface(kbps)"
    ::= { slot9ModuleIfEntry 25 }

slot9ModuleifInOctetsRate OBJECT-TYPE
    SYNTAX      Counter64
    MAX-ACCESS  read-only
    STATUS      current
    DESCRIPTION
            "The speed of octets received on the interface(kbps)"
    ::= { slot9ModuleIfEntry 26 }

slot9ModuleifOutPktsRate OBJECT-TYPE
    SYNTAX      Counter64
    MAX-ACCESS  read-only
    STATUS      current
    DESCRIPTION
            "The speed of packets trans on the interface(pps)"
    ::= { slot9ModuleIfEntry 27 }

slot9ModuleifInPktsRate OBJECT-TYPE
    SYNTAX      Counter64
    MAX-ACCESS  read-only
    STATUS      current
    DESCRIPTION
            "The speed of octets received on the interface(kbps)"
    ::= { slot9ModuleIfEntry 28 }

slot9ModuleifRxPower OBJECT-TYPE
    SYNTAX      DisplayString (SIZE (0..255))
    MAX-ACCESS  read-only
    STATUS      current
    DESCRIPTION
            "the value of interface's received power, in dbm format."
    ::= { slot9ModuleIfEntry 29 }

slot9ModuleifTxPower OBJECT-TYPE
    SYNTAX      DisplayString (SIZE (0..255))
    MAX-ACCESS  read-only
    STATUS      current
    DESCRIPTION
            "the value of interface's send power, in dbm format."
    ::= { slot9ModuleIfEntry 30 }

slot9ModuleifSpecific OBJECT-TYPE
    SYNTAX      OBJECT IDENTIFIER
    MAX-ACCESS  read-only
    STATUS      deprecated
    DESCRIPTION
            "A reference to MIB definitions specific to the particular
            media being used to realize the interface.  It is

            recommended that this value point to an instance of a MIB
            object in the media-specific MIB, i.e., that this object
            have the semantics associated with the InstancePointer
            textual convention defined in RFC 2579.  In fact, it is
            recommended that the media-specific MIB specify what value
            ifSpecific should/can take for values of ifType.  If no MIB
            definitions specific to the particular media are available,
            the value should be set to the OBJECT IDENTIFIER { 0 0 }."
    ::= { slot9ModuleIfEntry 31 }  
   
slot9ModuleifTxMirrorList OBJECT-TYPE
    SYNTAX      DisplayString (SIZE (0..255))
    MAX-ACCESS  read-only
    STATUS      deprecated
    DESCRIPTION
            "the interface tx mirror list."
    ::= { slot9ModuleIfEntry 32 }  
 
slot9ModuleifRxMirrorList OBJECT-TYPE
    SYNTAX      DisplayString (SIZE (0..255))
    MAX-ACCESS  read-only
    STATUS      deprecated
    DESCRIPTION
            "the interface rx mirror list."
    ::= { slot9ModuleIfEntry 33 }  
  
slot9ModuleifRxPowerMin OBJECT-TYPE
    SYNTAX      DisplayString (SIZE (0..255))
    MAX-ACCESS  read-only
    STATUS      deprecated
    DESCRIPTION
            "the interface min rx power."
    ::= { slot9ModuleIfEntry 34 }  

slot9ModuleifRxPowerMax OBJECT-TYPE
    SYNTAX      DisplayString (SIZE (0..255))
    MAX-ACCESS  read-only
    STATUS      deprecated
    DESCRIPTION
            "the interface max rx power."
    ::= { slot9ModuleIfEntry 35 }  

slot9ModuleifTxPowerMin OBJECT-TYPE
    SYNTAX      DisplayString (SIZE (0..255))
    MAX-ACCESS  read-only
    STATUS      deprecated
    DESCRIPTION
            "the interface min tx power."
    ::= { slot9ModuleIfEntry 36 }  

slot9ModuleifTxPowerMax OBJECT-TYPE
    SYNTAX      DisplayString (SIZE (0..255))
    MAX-ACCESS  read-only
    STATUS      deprecated
    DESCRIPTION
            "the interface max tx power."
    ::= { slot9ModuleIfEntry 37 }  

slot9ModuleifRxHisPeak OBJECT-TYPE
    SYNTAX      Counter64
    MAX-ACCESS  read-only
    STATUS      current
    DESCRIPTION
            "The max speed of rx rate on the interface(kbps)"
    ::= { slot9ModuleIfEntry 38 }

slot9ModuleifTxHisPeak OBJECT-TYPE
    SYNTAX      Counter64
    MAX-ACCESS  read-only
    STATUS      current
    DESCRIPTION
            "The max speed of tx rate on the interface(kbps)"
    ::= { slot9ModuleIfEntry 39 }

slot9ModuleifMode OBJECT-TYPE
    SYNTAX      DisplayString (SIZE (0..255))
    MAX-ACCESS  read-only
    STATUS      deprecated
    DESCRIPTION
            "the interface if mode."
    ::= { slot9ModuleIfEntry 40 }  

-- slot 10 --

-- slot10Table --

slot10Table OBJECT-TYPE
    SYNTAX      SEQUENCE OF Slot10Entry
    MAX-ACCESS  not-accessible
    STATUS      current
    DESCRIPTION
            "A list of all slot10Type's utilization."
    ::= { slot10 1 }  

slot10Entry OBJECT-TYPE
    SYNTAX      Slot10Entry
    MAX-ACCESS  not-accessible
    STATUS      current
    DESCRIPTION
            "An entry contains a slot10's utilization."
    INDEX   { slot10Index }
    ::= { slot10Table 1 }

Slot10Entry ::=
    SEQUENCE {     
		slot10Index                       Integer32,
		slot10Type                        DisplayString,
		slot10Status                      DisplayString,		
        slot10SerialNumber                DisplayString,		
        slot10Temperature                 DisplayString
    }  

slot10Index OBJECT-TYPE
    SYNTAX      Integer32 (1..2147483647)
    MAX-ACCESS  not-accessible
    STATUS      current
    DESCRIPTION
            "A unique value, greater than zero, for each chassis`s slot10."
    ::= { slot10Entry 1 }

slot10Type OBJECT-TYPE
    SYNTAX      DisplayString (SIZE (0..255))
    MAX-ACCESS  read-only
    STATUS      current
    DESCRIPTION
            "the slot10Type of each chassis."
    ::= { slot10Entry 2 }

slot10Status OBJECT-TYPE
    SYNTAX      DisplayString (SIZE (0..255))
    MAX-ACCESS  read-only
    STATUS      current
    DESCRIPTION
            "A string to describe the board status." 
   ::= { slot10Entry 3 }   
 
slot10SerialNumber OBJECT-TYPE
    SYNTAX      DisplayString (SIZE (0..255))
    MAX-ACCESS  read-only
    STATUS      current
    DESCRIPTION
            "A string to describe the board serial number." 
    ::= { slot10Entry 4 }   

slot10Temperature OBJECT-TYPE
    SYNTAX      DisplayString (SIZE (0..255))
    MAX-ACCESS  read-only
    STATUS      current
    DESCRIPTION
            "A string to describe the board temperature." 
    ::= { slot10Entry 5 }   

slot10Module OBJECT IDENTIFIER ::= { slot10 2 }

-- slot10ModuleTable --
slot10ModuleTable OBJECT-TYPE
    SYNTAX      SEQUENCE OF Slot10ModuleEntry
    MAX-ACCESS  not-accessible
    STATUS      current
    DESCRIPTION
            "A list of all slot10Module's utilization."
    ::= { slot10Module 1 }  

slot10ModuleEntry OBJECT-TYPE
    SYNTAX      Slot10ModuleEntry
    MAX-ACCESS  not-accessible
    STATUS      current
    DESCRIPTION
            "An entry contains a slot10Module's utilization."
    INDEX   { slot10ModuleIndex }
    ::= { slot10ModuleTable 1 }

Slot10ModuleEntry ::=
    SEQUENCE {     
		slot10ModuleIndex                       Integer32,
		slot10ModuleId                           DisplayString,  
		slot10ModuleIfNumber                     Integer32		
    } 

slot10ModuleIndex OBJECT-TYPE
    SYNTAX      Integer32 (1..2147483647)
    MAX-ACCESS  not-accessible
    STATUS      current
    DESCRIPTION
            "A unique value, greater than zero, for each chassis`s slot10."
    ::= { slot10ModuleEntry 1 }

slot10ModuleId OBJECT-TYPE
    SYNTAX      DisplayString (SIZE (0..32))
    MAX-ACCESS  read-only
    STATUS      current
    DESCRIPTION
            "the value of module`s id"
    ::= { slot10ModuleEntry 2 }
  
slot10ModuleIfNumber OBJECT-TYPE
    SYNTAX      Integer32(0..2147483647)
    MAX-ACCESS  read-only
    STATUS      current
    DESCRIPTION
            "The number of network interfaces (regardless of their
            current state) present on this system." 
    ::= { slot10ModuleEntry 3 } 
    
slot10ModuleIfTable OBJECT-TYPE
    SYNTAX      SEQUENCE OF Slot10ModuleIfEntry
    MAX-ACCESS  not-accessible
    STATUS      current
    DESCRIPTION
            "A list of interface entries.  The number of entries is
            given by the value of ifNumber."
    ::= { slot10Module 2 } 
    
slot10ModuleIfEntry OBJECT-TYPE
    SYNTAX      Slot10ModuleIfEntry
    MAX-ACCESS  not-accessible
    STATUS      current
    DESCRIPTION
            "An entry containing management information applicable to a
            particular interface."
    INDEX   { slot10ModuleifIndex }
    ::= { slot10ModuleIfTable 1 }
    
Slot10ModuleIfEntry ::=
    SEQUENCE {
        slot10ModuleifIndex                 InterfaceIndex,  
        slot10ModuleIfId                    DisplayString,  
        slot10ModuleifDescr                 DisplayString,           
        slot10ModuleifType                  IANAifType,   		
        slot10ModuleifMtu                   Integer32,                
        slot10ModuleifSpeed                 Counter64,               
        slot10ModuleifPhysAddress           PhysAddress,              
        slot10ModuleifAdminStatus           INTEGER,                  
        slot10ModuleifOperStatus            INTEGER,                  
        slot10ModuleifLastChange            TimeTicks,                
        slot10ModuleifInOctets              Counter64,                
        slot10ModuleifInUcastPkts           Counter64,                
        slot10ModuleifInNUcastPkts          Counter64,  
        slot10ModuleifInDiscards            Counter64,
        slot10ModuleifInErrors              Counter64,
        slot10ModuleifInFcsErrorPkts        Counter64,
        slot10ModuleifInUnknownProtos       Counter64,	-- deprecated
        slot10ModuleifOutOctets             Counter64,
        slot10ModuleifOutUcastPkts          Counter64,
        slot10ModuleifOutNUcastPkts         Counter64,  -- deprecated
        slot10ModuleifOutDiscards           Counter64,
        slot10ModuleifOutErrors             Counter64,
        slot10ModuleifOutFcsErrorPkts       Counter64,
        slot10ModuleifOutQLen               Gauge32,    -- deprecated  
        slot10ModuleifOutOctetsRate         Counter64,
        slot10ModuleifInOctetsRate          Counter64,
        slot10ModuleifOutPktsRate           Counter64,
        slot10ModuleifInPktsRate            Counter64,
        slot10ModuleifRxPower               DisplayString,
        slot10ModuleifTxPower               DisplayString,
        slot10ModuleifSpecific              OBJECT IDENTIFIER,
        slot10ModuleifTxMirrorList          DisplayString,
        slot10ModuleifRxMirrorList          DisplayString,
        slot10ModuleifRxPowerMin               DisplayString,
        slot10ModuleifRxPowerMax               DisplayString,
        slot10ModuleifTxPowerMin               DisplayString,
        slot10ModuleifTxPowerMax               DisplayString,
        slot10ModuleifRxHisPeak            Counter64,
        slot10ModuleifTxHisPeak            Counter64,
        slot10ModuleifMode                 DisplayString   		
    }         

slot10ModuleifIndex OBJECT-TYPE
    SYNTAX      InterfaceIndex
    MAX-ACCESS  read-only
    STATUS      current
    DESCRIPTION
            "A unique value, greater than zero, for each interface.  It
            is recommended that values are assigned contiguously
            starting from 1.  The value for each interface sub-layer
            must remain constant at least from one re-initialization of
            the entity's network management system to the next re-
            initialization."
    ::= { slot10ModuleIfEntry 1 }
    
slot10ModuleIfId OBJECT-TYPE
    SYNTAX      DisplayString (SIZE (0..32))
    MAX-ACCESS  read-only
    STATUS      current
    DESCRIPTION
            "the value of module`s id"
    ::= { slot10ModuleIfEntry 2 }
    
slot10ModuleifDescr OBJECT-TYPE
    SYNTAX      DisplayString (SIZE (0..255))
    MAX-ACCESS  read-only
    STATUS      current
    DESCRIPTION
            "A textual string containing information about the
            interface.  This string should include the name of the
            manufacturer, the product name and the version of the
            interface hardware/software."
    ::= { slot10ModuleIfEntry 3 }
    
slot10ModuleifType OBJECT-TYPE
    SYNTAX      IANAifType
    MAX-ACCESS  read-only
    STATUS      current
    DESCRIPTION
            "The type of interface.  Additional values for ifType are
            assigned by the Internet Assigned Numbers Authority (IANA),
            through updating the syntax of the IANAifType textual
            convention."
    ::= { slot10ModuleIfEntry 4 }

slot10ModuleifMtu OBJECT-TYPE
    SYNTAX      Integer32(1..2147483647)
    MAX-ACCESS  read-only
    STATUS      current
    DESCRIPTION
            "The size of the largest packet which can be sent/received
            on the interface, specified in octets.  For interfaces that
            are used for transmitting network datagrams, this is the
            size of the largest network datagram that can be sent on the
            interface."
    ::= { slot10ModuleIfEntry 5 }

slot10ModuleifSpeed OBJECT-TYPE
    SYNTAX      Counter64
    MAX-ACCESS  read-only
    STATUS      current
    DESCRIPTION
            "An estimate of the interface's current bandwidth in bits
            per second.  For interfaces which do not vary in bandwidth
            or for those where no accurate estimation can be made, this
            object should contain the nominal bandwidth. For a sub-layer
            which has no concept of bandwidth, this object should be zero."
    ::= { slot10ModuleIfEntry 6 }

slot10ModuleifPhysAddress OBJECT-TYPE
    SYNTAX      PhysAddress
    MAX-ACCESS  read-only
    STATUS      current
    DESCRIPTION
            "The interface's address at its protocol sub-layer.  For
            example, for an 802.x interface, this object normally
            contains a MAC address.  The interface's media-specific MIB
            must define the bit and byte ordering and the format of the
            value of this object.  For interfaces which do not have such
            an address (e.g., a serial line), this object should contain
            an octet string of zero length."
    ::= { slot10ModuleIfEntry 7 }
    
slot10ModuleifAdminStatus OBJECT-TYPE
    SYNTAX  INTEGER {
                up(1),       -- ready to pass packets
                down(2),
                testing(3)   -- in some test mode
            }
    MAX-ACCESS  read-write
    STATUS      current
    DESCRIPTION
            "The desired state of the interface.  The testing(3) state
            indicates that no operational packets can be passed.  When a
            managed system initializes, all interfaces start with
            ifAdminStatus in the down(2) state.  As a result of either
            explicit management action or per configuration information
            retained by the managed system, ifAdminStatus is then
            changed to either the up(1) or testing(3) states (or remains
            in the down(2) state)."
    ::= { slot10ModuleIfEntry 8 }

slot10ModuleifOperStatus OBJECT-TYPE
    SYNTAX  INTEGER {
                up(1),        -- ready to pass packets
                down(2),
                testing(3),   -- in some test mode
                unknown(4),   -- status can not be determined
                              -- for some reason.
                dormant(5),
                notPresent(6),    -- some component is missing
                lowerLayerDown(7) -- down due to state of
                                  -- lower-layer interface(s)
            }
    MAX-ACCESS  read-only
    STATUS      current
    DESCRIPTION
            "The current operational state of the interface.  The
            testing(3) state indicates that no operational packets can
            be passed.  If ifAdminStatus is down(2) then ifOperStatus
            should be down(2).  If ifAdminStatus is changed to up(1)
            then ifOperStatus should change to up(1) if the interface is
            ready to transmit and receive network traffic; it should
            change to dormant(5) if the interface is waiting for
            external actions (such as a serial line waiting for an
            incoming connection); it should remain in the down(2) state
            if and only if there is a fault that prevents it from going
            to the up(1) state; it should remain in the notPresent(6)
            state if the interface has missing (typically, hardware)
            components."
    ::= { slot10ModuleIfEntry 9 }

slot10ModuleifLastChange OBJECT-TYPE
    SYNTAX      TimeTicks
    MAX-ACCESS  read-only
    STATUS      current
    DESCRIPTION
            "The value of sysUpTime at the time the interface entered
            its current operational state.  If the current state was
            entered prior to the last re-initialization of the local
            network management subsystem, then this object contains a
            zero value."
    ::= { slot10ModuleIfEntry 10 }

slot10ModuleifInOctets OBJECT-TYPE
    SYNTAX      Counter64
    MAX-ACCESS  read-only
    STATUS      current
    DESCRIPTION
            "The total number of octets received on the interface,
            including framing characters.

            Discontinuities in the value of this counter can occur at
            re-initialization of the management system, and at other
            times as indicated by the value of
            ifCounterDiscontinuityTime."
    ::= { slot10ModuleIfEntry 11 }

slot10ModuleifInUcastPkts OBJECT-TYPE
    SYNTAX      Counter64
    MAX-ACCESS  read-only
    STATUS      current
    DESCRIPTION
            "The number of packets, delivered by this sub-layer to a
            higher (sub-)layer, which were not addressed to a multicast
            or broadcast address at this sub-layer.

            Discontinuities in the value of this counter can occur at
            re-initialization of the management system, and at other
            times as indicated by the value of
            ifCounterDiscontinuityTime."
    ::= { slot10ModuleIfEntry 12 }

slot10ModuleifInNUcastPkts OBJECT-TYPE
    SYNTAX  Counter64
    MAX-ACCESS  read-only
    STATUS      current
    DESCRIPTION
            "The number of packets, delivered by this sub-layer to a
            higher (sub-)layer, which were addressed to a multicast or
            broadcast address at this sub-layer.

            Discontinuities in the value of this counter can occur at
            re-initialization of the management system, and at other
            times as indicated by the value of
            ifCounterDiscontinuityTime.

            This object is deprecated in favour of ifInMulticastPkts and
            ifInBroadcastPkts."
    ::= { slot10ModuleIfEntry 13 }

slot10ModuleifInDiscards OBJECT-TYPE
    SYNTAX      Counter64
    MAX-ACCESS  read-only
    STATUS      current
    DESCRIPTION
            "The number of inbound packets which were chosen to be
            discarded even though no errors had been detected to prevent

            their being deliverable to a higher-layer protocol.  One
            possible reason for discarding such a packet could be to
            free up buffer space.

            Discontinuities in the value of this counter can occur at
            re-initialization of the management system, and at other
            times as indicated by the value of
            ifCounterDiscontinuityTime."
    ::= { slot10ModuleIfEntry 14 }

slot10ModuleifInErrors OBJECT-TYPE
    SYNTAX      Counter64
    MAX-ACCESS  read-only
    STATUS      current
    DESCRIPTION
            "For packet-oriented interfaces, the number of inbound
            packets that contained errors preventing them from being
            deliverable to a higher-layer protocol.  For character-
            oriented or fixed-length interfaces, the number of inbound
            transmission units that contained errors preventing them
            from being deliverable to a higher-layer protocol.

            Discontinuities in the value of this counter can occur at
            re-initialization of the management system, and at other
            times as indicated by the value of
            ifCounterDiscontinuityTime."
    ::= { slot10ModuleIfEntry 15 }

slot10ModuleifInFcsErrorPkts OBJECT-TYPE
    SYNTAX      Counter64
    MAX-ACCESS  read-only
    STATUS      current
    DESCRIPTION
            "FCS error pakets."
    ::= { slot10ModuleIfEntry 16 }

slot10ModuleifInUnknownProtos OBJECT-TYPE
    SYNTAX      Counter64
    MAX-ACCESS  read-only
    STATUS      current
    DESCRIPTION
            "For packet-oriented interfaces, the number of packets
            received via the interface which were discarded because of
            an unknown or unsupported protocol.  For character-oriented
            or fixed-length interfaces that support protocol
            multiplexing the number of transmission units received via
            the interface which were discarded because of an unknown or
            unsupported protocol.  For any interface that does not
            support protocol multiplexing, this counter will always be
            0.

            Discontinuities in the value of this counter can occur at
            re-initialization of the management system, and at other
            times as indicated by the value of
            ifCounterDiscontinuityTime."
    ::= { slot10ModuleIfEntry 17 }

slot10ModuleifOutOctets OBJECT-TYPE
    SYNTAX      Counter64
    MAX-ACCESS  read-only
    STATUS      current
    DESCRIPTION
            "The total number of octets transmitted out of the
            interface, including framing characters.

            Discontinuities in the value of this counter can occur at
            re-initialization of the management system, and at other
            times as indicated by the value of
            ifCounterDiscontinuityTime."
    ::= { slot10ModuleIfEntry 18 }

slot10ModuleifOutUcastPkts OBJECT-TYPE
    SYNTAX      Counter64
    MAX-ACCESS  read-only
    STATUS      current
    DESCRIPTION
            "The total number of packets that higher-level protocols
            requested be transmitted, and which were not addressed to a
            multicast or broadcast address at this sub-layer, including
            those that were discarded or not sent.

            Discontinuities in the value of this counter can occur at
            re-initialization of the management system, and at other
            times as indicated by the value of
            ifCounterDiscontinuityTime."
    ::= { slot10ModuleIfEntry 19 }

slot10ModuleifOutNUcastPkts OBJECT-TYPE
    SYNTAX      Counter64
    MAX-ACCESS  read-only
    STATUS      deprecated
    DESCRIPTION
            "The total number of packets that higher-level protocols
            requested be transmitted, and which were addressed to a
            multicast or broadcast address at this sub-layer, including
            those that were discarded or not sent.

            Discontinuities in the value of this counter can occur at
            re-initialization of the management system, and at other
            times as indicated by the value of
            ifCounterDiscontinuityTime.

            This object is deprecated in favour of ifOutMulticastPkts
            and ifOutBroadcastPkts."
    ::= { slot10ModuleIfEntry 20 }

slot10ModuleifOutDiscards OBJECT-TYPE
    SYNTAX      Counter64
    MAX-ACCESS  read-only
    STATUS      current
    DESCRIPTION
            "The number of outbound packets which were chosen to be
            discarded even though no errors had been detected to prevent
            their being transmitted.  One possible reason for discarding
            such a packet could be to free up buffer space.

            Discontinuities in the value of this counter can occur at
            re-initialization of the management system, and at other
            times as indicated by the value of
            ifCounterDiscontinuityTime."
    ::= { slot10ModuleIfEntry 21 }

slot10ModuleifOutErrors OBJECT-TYPE
    SYNTAX      Counter64
    MAX-ACCESS  read-only
    STATUS      current
    DESCRIPTION
            "For packet-oriented interfaces, the number of outbound
            packets that could not be transmitted because of errors.
            For character-oriented or fixed-length interfaces, the
            number of outbound transmission units that could not be
            transmitted because of errors.

            Discontinuities in the value of this counter can occur at
            re-initialization of the management system, and at other
            times as indicated by the value of
            ifCounterDiscontinuityTime."
    ::= { slot10ModuleIfEntry 22 }

slot10ModuleifOutFcsErrorPkts OBJECT-TYPE
    SYNTAX      Counter64
    MAX-ACCESS  read-only
    STATUS      current
    DESCRIPTION
            "FCS error pakets."
    ::= { slot10ModuleIfEntry 23 }

slot10ModuleifOutQLen OBJECT-TYPE
    SYNTAX      Gauge32
    MAX-ACCESS  read-only
    STATUS      deprecated
    DESCRIPTION
            "The length of the output packet queue (in packets)."
    ::= { slot10ModuleIfEntry 24 }

slot10ModuleifOutOctetsRate OBJECT-TYPE
    SYNTAX      Counter64
    MAX-ACCESS  read-only
    STATUS      current
    DESCRIPTION
            "The speed of octets trans on the interface(kbps)"
    ::= { slot10ModuleIfEntry 25 }

slot10ModuleifInOctetsRate OBJECT-TYPE
    SYNTAX      Counter64
    MAX-ACCESS  read-only
    STATUS      current
    DESCRIPTION
            "The speed of octets received on the interface(kbps)"
    ::= { slot10ModuleIfEntry 26 }

slot10ModuleifOutPktsRate OBJECT-TYPE
    SYNTAX      Counter64
    MAX-ACCESS  read-only
    STATUS      current
    DESCRIPTION
            "The speed of packets trans on the interface(pps)"
    ::= { slot10ModuleIfEntry 27 }

slot10ModuleifInPktsRate OBJECT-TYPE
    SYNTAX      Counter64
    MAX-ACCESS  read-only
    STATUS      current
    DESCRIPTION
            "The speed of octets received on the interface(kbps)"
    ::= { slot10ModuleIfEntry 28 }

slot10ModuleifRxPower OBJECT-TYPE
    SYNTAX      DisplayString (SIZE (0..255))
    MAX-ACCESS  read-only
    STATUS      current
    DESCRIPTION
            "the value of interface's received power, in dbm format."
    ::= { slot10ModuleIfEntry 29 }

slot10ModuleifTxPower OBJECT-TYPE
    SYNTAX      DisplayString (SIZE (0..255))
    MAX-ACCESS  read-only
    STATUS      current
    DESCRIPTION
            "the value of interface's send power, in dbm format."
    ::= { slot10ModuleIfEntry 30 }

slot10ModuleifSpecific OBJECT-TYPE
    SYNTAX      OBJECT IDENTIFIER
    MAX-ACCESS  read-only
    STATUS      deprecated
    DESCRIPTION
            "A reference to MIB definitions specific to the particular
            media being used to realize the interface.  It is

            recommended that this value point to an instance of a MIB
            object in the media-specific MIB, i.e., that this object
            have the semantics associated with the InstancePointer
            textual convention defined in RFC 2579.  In fact, it is
            recommended that the media-specific MIB specify what value
            ifSpecific should/can take for values of ifType.  If no MIB
            definitions specific to the particular media are available,
            the value should be set to the OBJECT IDENTIFIER { 0 0 }."
    ::= { slot10ModuleIfEntry 31 }  
   
slot10ModuleifTxMirrorList OBJECT-TYPE
    SYNTAX      DisplayString (SIZE (0..255))
    MAX-ACCESS  read-only
    STATUS      deprecated
    DESCRIPTION
            "the interface tx mirror list."
    ::= { slot10ModuleIfEntry 32 }  
 
slot10ModuleifRxMirrorList OBJECT-TYPE
    SYNTAX      DisplayString (SIZE (0..255))
    MAX-ACCESS  read-only
    STATUS      deprecated
    DESCRIPTION
            "the interface rx mirror list."
    ::= { slot10ModuleIfEntry 33 }  
  
slot10ModuleifRxPowerMin OBJECT-TYPE
    SYNTAX      DisplayString (SIZE (0..255))
    MAX-ACCESS  read-only
    STATUS      deprecated
    DESCRIPTION
            "the interface min rx power."
    ::= { slot10ModuleIfEntry 34 }  

slot10ModuleifRxPowerMax OBJECT-TYPE
    SYNTAX      DisplayString (SIZE (0..255))
    MAX-ACCESS  read-only
    STATUS      deprecated
    DESCRIPTION
            "the interface max rx power."
    ::= { slot10ModuleIfEntry 35 }  

slot10ModuleifTxPowerMin OBJECT-TYPE
    SYNTAX      DisplayString (SIZE (0..255))
    MAX-ACCESS  read-only
    STATUS      deprecated
    DESCRIPTION
            "the interface min tx power."
    ::= { slot10ModuleIfEntry 36 }  

slot10ModuleifTxPowerMax OBJECT-TYPE
    SYNTAX      DisplayString (SIZE (0..255))
    MAX-ACCESS  read-only
    STATUS      deprecated
    DESCRIPTION
            "the interface max tx power."
    ::= { slot10ModuleIfEntry 37 }  

slot10ModuleifRxHisPeak OBJECT-TYPE
    SYNTAX      Counter64
    MAX-ACCESS  read-only
    STATUS      current
    DESCRIPTION
            "The max speed of rx rate on the interface(kbps)"
    ::= { slot10ModuleIfEntry 38 }

slot10ModuleifTxHisPeak OBJECT-TYPE
    SYNTAX      Counter64
    MAX-ACCESS  read-only
    STATUS      current
    DESCRIPTION
            "The max speed of tx rate on the interface(kbps)"
    ::= { slot10ModuleIfEntry 39 }

slot10ModuleifMode OBJECT-TYPE
    SYNTAX      DisplayString (SIZE (0..255))
    MAX-ACCESS  read-only
    STATUS      deprecated
    DESCRIPTION
            "the interface if mode."
    ::= { slot10ModuleIfEntry 40 }  

-- slot 11 --

-- slot11Table --

slot11Table OBJECT-TYPE
    SYNTAX      SEQUENCE OF Slot11Entry
    MAX-ACCESS  not-accessible
    STATUS      current
    DESCRIPTION
            "A list of all slot11Type's utilization."
    ::= { slot11 1 }  

slot11Entry OBJECT-TYPE
    SYNTAX      Slot11Entry
    MAX-ACCESS  not-accessible
    STATUS      current
    DESCRIPTION
            "An entry contains a slot11's utilization."
    INDEX   { slot11Index }
    ::= { slot11Table 1 }

Slot11Entry ::=
    SEQUENCE {     
		slot11Index                       Integer32,
		slot11Type                        DisplayString,
		slot11Status                      DisplayString,		
        slot11SerialNumber                DisplayString,		
        slot11Temperature                 DisplayString
    }  

slot11Index OBJECT-TYPE
    SYNTAX      Integer32 (1..2147483647)
    MAX-ACCESS  not-accessible
    STATUS      current
    DESCRIPTION
            "A unique value, greater than zero, for each chassis`s slot11."
    ::= { slot11Entry 1 }

slot11Type OBJECT-TYPE
    SYNTAX      DisplayString (SIZE (0..255))
    MAX-ACCESS  read-only
    STATUS      current
    DESCRIPTION
            "the slot11Type of each chassis."
    ::= { slot11Entry 2 }

slot11Status OBJECT-TYPE
    SYNTAX      DisplayString (SIZE (0..255))
    MAX-ACCESS  read-only
    STATUS      current
    DESCRIPTION
            "A string to describe the board status." 
    ::= { slot11Entry 3 }   

slot11SerialNumber OBJECT-TYPE
    SYNTAX      DisplayString (SIZE (0..255))
    MAX-ACCESS  read-only
    STATUS      current
    DESCRIPTION
            "A string to describe the board serial number." 
    ::= { slot11Entry 4 }   

slot11Temperature OBJECT-TYPE
    SYNTAX      DisplayString (SIZE (0..255))
    MAX-ACCESS  read-only
    STATUS      current
    DESCRIPTION
            "A string to describe the board temperature." 
    ::= { slot11Entry 5 }   


slot11Module OBJECT IDENTIFIER ::= { slot11 2 }

-- slot11ModuleTable --
slot11ModuleTable OBJECT-TYPE
    SYNTAX      SEQUENCE OF Slot11ModuleEntry
    MAX-ACCESS  not-accessible
    STATUS      current
    DESCRIPTION
            "A list of all slot11Module's utilization."
    ::= { slot11Module 1 }  

slot11ModuleEntry OBJECT-TYPE
    SYNTAX      Slot11ModuleEntry
    MAX-ACCESS  not-accessible
    STATUS      current
    DESCRIPTION
            "An entry contains a slot11Module's utilization."
    INDEX   { slot11ModuleIndex }
    ::= { slot11ModuleTable 1 }

Slot11ModuleEntry ::=
    SEQUENCE {     
		slot11ModuleIndex                       Integer32,
		slot11ModuleId                           DisplayString,  
		slot11ModuleIfNumber                     Integer32		
    } 

slot11ModuleIndex OBJECT-TYPE
    SYNTAX      Integer32 (1..2147483647)
    MAX-ACCESS  not-accessible
    STATUS      current
    DESCRIPTION
            "A unique value, greater than zero, for each chassis`s slot11."
    ::= { slot11ModuleEntry 1 }

slot11ModuleId OBJECT-TYPE
    SYNTAX      DisplayString (SIZE (0..32))
    MAX-ACCESS  read-only
    STATUS      current
    DESCRIPTION
            "the value of module`s id"
    ::= { slot11ModuleEntry 2 }
  
slot11ModuleIfNumber OBJECT-TYPE
    SYNTAX      Integer32(0..2147483647)
    MAX-ACCESS  read-only
    STATUS      current
    DESCRIPTION
            "The number of network interfaces (regardless of their
            current state) present on this system." 
    ::= { slot11ModuleEntry 3 } 
    
slot11ModuleIfTable OBJECT-TYPE
    SYNTAX      SEQUENCE OF Slot11ModuleIfEntry
    MAX-ACCESS  not-accessible
    STATUS      current
    DESCRIPTION
            "A list of interface entries.  The number of entries is
            given by the value of ifNumber."
    ::= { slot11Module 2 } 
    
slot11ModuleIfEntry OBJECT-TYPE
    SYNTAX      Slot11ModuleIfEntry
    MAX-ACCESS  not-accessible
    STATUS      current
    DESCRIPTION
            "An entry containing management information applicable to a
            particular interface."
    INDEX   { slot11ModuleifIndex }
    ::= { slot11ModuleIfTable 1 }
    
Slot11ModuleIfEntry ::=
    SEQUENCE {
        slot11ModuleifIndex                 InterfaceIndex,  
        slot11ModuleIfId                    DisplayString,  
        slot11ModuleifDescr                 DisplayString,           
        slot11ModuleifType                  IANAifType,   		
        slot11ModuleifMtu                   Integer32,                
        slot11ModuleifSpeed                 Counter64,               
        slot11ModuleifPhysAddress           PhysAddress,              
        slot11ModuleifAdminStatus           INTEGER,                  
        slot11ModuleifOperStatus            INTEGER,                  
        slot11ModuleifLastChange            TimeTicks,                
        slot11ModuleifInOctets              Counter64,                
        slot11ModuleifInUcastPkts           Counter64,                
        slot11ModuleifInNUcastPkts          Counter64,  
        slot11ModuleifInDiscards            Counter64,
        slot11ModuleifInErrors              Counter64,
        slot11ModuleifInFcsErrorPkts        Counter64,
        slot11ModuleifInUnknownProtos       Counter64,	-- deprecated
        slot11ModuleifOutOctets             Counter64,
        slot11ModuleifOutUcastPkts          Counter64,
        slot11ModuleifOutNUcastPkts         Counter64,  -- deprecated
        slot11ModuleifOutDiscards           Counter64,
        slot11ModuleifOutErrors             Counter64,
        slot11ModuleifOutFcsErrorPkts       Counter64,
        slot11ModuleifOutQLen               Gauge32,    -- deprecated  
        slot11ModuleifOutOctetsRate         Counter64,
        slot11ModuleifInOctetsRate          Counter64,
        slot11ModuleifOutPktsRate           Counter64,
        slot11ModuleifInPktsRate            Counter64,
        slot11ModuleifRxPower               DisplayString,
        slot11ModuleifTxPower               DisplayString,
        slot11ModuleifSpecific              OBJECT IDENTIFIER,
        slot11ModuleifTxMirrorList          DisplayString,
        slot11ModuleifRxMirrorList          DisplayString,
        slot11ModuleifRxPowerMin               DisplayString,
        slot11ModuleifRxPowerMax               DisplayString,
        slot11ModuleifTxPowerMin               DisplayString,
        slot11ModuleifTxPowerMax               DisplayString,
        slot11ModuleifRxHisPeak            Counter64,
        slot11ModuleifTxHisPeak            Counter64,
        slot11ModuleifMode                 DisplayString   		
    }         

slot11ModuleifIndex OBJECT-TYPE
    SYNTAX      InterfaceIndex
    MAX-ACCESS  read-only
    STATUS      current
    DESCRIPTION
            "A unique value, greater than zero, for each interface.  It
            is recommended that values are assigned contiguously
            starting from 1.  The value for each interface sub-layer
            must remain constant at least from one re-initialization of
            the entity's network management system to the next re-
            initialization."
    ::= { slot11ModuleIfEntry 1 }
    
slot11ModuleIfId OBJECT-TYPE
    SYNTAX      DisplayString (SIZE (0..32))
    MAX-ACCESS  read-only
    STATUS      current
    DESCRIPTION
            "the value of module`s id"
    ::= { slot11ModuleIfEntry 2 }
    
slot11ModuleifDescr OBJECT-TYPE
    SYNTAX      DisplayString (SIZE (0..255))
    MAX-ACCESS  read-only
    STATUS      current
    DESCRIPTION
            "A textual string containing information about the
            interface.  This string should include the name of the
            manufacturer, the product name and the version of the
            interface hardware/software."
    ::= { slot11ModuleIfEntry 3 }
    
slot11ModuleifType OBJECT-TYPE
    SYNTAX      IANAifType
    MAX-ACCESS  read-only
    STATUS      current
    DESCRIPTION
            "The type of interface.  Additional values for ifType are
            assigned by the Internet Assigned Numbers Authority (IANA),
            through updating the syntax of the IANAifType textual
            convention."
    ::= { slot11ModuleIfEntry 4 }

slot11ModuleifMtu OBJECT-TYPE
    SYNTAX      Integer32(1..2147483647)
    MAX-ACCESS  read-only
    STATUS      current
    DESCRIPTION
            "The size of the largest packet which can be sent/received
            on the interface, specified in octets.  For interfaces that
            are used for transmitting network datagrams, this is the
            size of the largest network datagram that can be sent on the
            interface."
    ::= { slot11ModuleIfEntry 5 }

slot11ModuleifSpeed OBJECT-TYPE
    SYNTAX      Counter64
    MAX-ACCESS  read-only
    STATUS      current
    DESCRIPTION
            "An estimate of the interface's current bandwidth in bits
            per second.  For interfaces which do not vary in bandwidth
            or for those where no accurate estimation can be made, this
            object should contain the nominal bandwidth. For a sub-layer
            which has no concept of bandwidth, this object should be zero."
    ::= { slot11ModuleIfEntry 6 }

slot11ModuleifPhysAddress OBJECT-TYPE
    SYNTAX      PhysAddress
    MAX-ACCESS  read-only
    STATUS      current
    DESCRIPTION
            "The interface's address at its protocol sub-layer.  For
            example, for an 802.x interface, this object normally
            contains a MAC address.  The interface's media-specific MIB
            must define the bit and byte ordering and the format of the
            value of this object.  For interfaces which do not have such
            an address (e.g., a serial line), this object should contain
            an octet string of zero length."
    ::= { slot11ModuleIfEntry 7 }
    
slot11ModuleifAdminStatus OBJECT-TYPE
    SYNTAX  INTEGER {
                up(1),       -- ready to pass packets
                down(2),
                testing(3)   -- in some test mode
            }
    MAX-ACCESS  read-write
    STATUS      current
    DESCRIPTION
            "The desired state of the interface.  The testing(3) state
            indicates that no operational packets can be passed.  When a
            managed system initializes, all interfaces start with
            ifAdminStatus in the down(2) state.  As a result of either
            explicit management action or per configuration information
            retained by the managed system, ifAdminStatus is then
            changed to either the up(1) or testing(3) states (or remains
            in the down(2) state)."
    ::= { slot11ModuleIfEntry 8 }

slot11ModuleifOperStatus OBJECT-TYPE
    SYNTAX  INTEGER {
                up(1),        -- ready to pass packets
                down(2),
                testing(3),   -- in some test mode
                unknown(4),   -- status can not be determined
                              -- for some reason.
                dormant(5),
                notPresent(6),    -- some component is missing
                lowerLayerDown(7) -- down due to state of
                                  -- lower-layer interface(s)
            }
    MAX-ACCESS  read-only
    STATUS      current
    DESCRIPTION
            "The current operational state of the interface.  The
            testing(3) state indicates that no operational packets can
            be passed.  If ifAdminStatus is down(2) then ifOperStatus
            should be down(2).  If ifAdminStatus is changed to up(1)
            then ifOperStatus should change to up(1) if the interface is
            ready to transmit and receive network traffic; it should
            change to dormant(5) if the interface is waiting for
            external actions (such as a serial line waiting for an
            incoming connection); it should remain in the down(2) state
            if and only if there is a fault that prevents it from going
            to the up(1) state; it should remain in the notPresent(6)
            state if the interface has missing (typically, hardware)
            components."
    ::= { slot11ModuleIfEntry 9 }

slot11ModuleifLastChange OBJECT-TYPE
    SYNTAX      TimeTicks
    MAX-ACCESS  read-only
    STATUS      current
    DESCRIPTION
            "The value of sysUpTime at the time the interface entered
            its current operational state.  If the current state was
            entered prior to the last re-initialization of the local
            network management subsystem, then this object contains a
            zero value."
    ::= { slot11ModuleIfEntry 10 }


slot11ModuleifInOctets OBJECT-TYPE
    SYNTAX      Counter64
    MAX-ACCESS  read-only
    STATUS      current
    DESCRIPTION
            "The total number of octets received on the interface,
            including framing characters.

            Discontinuities in the value of this counter can occur at
            re-initialization of the management system, and at other
            times as indicated by the value of
            ifCounterDiscontinuityTime."
    ::= { slot11ModuleIfEntry 11 }

slot11ModuleifInUcastPkts OBJECT-TYPE
    SYNTAX      Counter64
    MAX-ACCESS  read-only
    STATUS      current
    DESCRIPTION
            "The number of packets, delivered by this sub-layer to a
            higher (sub-)layer, which were not addressed to a multicast
            or broadcast address at this sub-layer.

            Discontinuities in the value of this counter can occur at
            re-initialization of the management system, and at other
            times as indicated by the value of
            ifCounterDiscontinuityTime."
    ::= { slot11ModuleIfEntry 12 }

slot11ModuleifInNUcastPkts OBJECT-TYPE
    SYNTAX  Counter64
    MAX-ACCESS  read-only
    STATUS      current
    DESCRIPTION
            "The number of packets, delivered by this sub-layer to a
            higher (sub-)layer, which were addressed to a multicast or
            broadcast address at this sub-layer.

            Discontinuities in the value of this counter can occur at
            re-initialization of the management system, and at other
            times as indicated by the value of
            ifCounterDiscontinuityTime.

            This object is deprecated in favour of ifInMulticastPkts and
            ifInBroadcastPkts."
    ::= { slot11ModuleIfEntry 13 }

slot11ModuleifInDiscards OBJECT-TYPE
    SYNTAX      Counter64
    MAX-ACCESS  read-only
    STATUS      current
    DESCRIPTION
            "The number of inbound packets which were chosen to be
            discarded even though no errors had been detected to prevent

            their being deliverable to a higher-layer protocol.  One
            possible reason for discarding such a packet could be to
            free up buffer space.

            Discontinuities in the value of this counter can occur at
            re-initialization of the management system, and at other
            times as indicated by the value of
            ifCounterDiscontinuityTime."
    ::= { slot11ModuleIfEntry 14 }

slot11ModuleifInErrors OBJECT-TYPE
    SYNTAX      Counter64
    MAX-ACCESS  read-only
    STATUS      current
    DESCRIPTION
            "For packet-oriented interfaces, the number of inbound
            packets that contained errors preventing them from being
            deliverable to a higher-layer protocol.  For character-
            oriented or fixed-length interfaces, the number of inbound
            transmission units that contained errors preventing them
            from being deliverable to a higher-layer protocol.

            Discontinuities in the value of this counter can occur at
            re-initialization of the management system, and at other
            times as indicated by the value of
            ifCounterDiscontinuityTime."
    ::= { slot11ModuleIfEntry 15 }

slot11ModuleifInFcsErrorPkts OBJECT-TYPE
    SYNTAX      Counter64
    MAX-ACCESS  read-only
    STATUS      current
    DESCRIPTION
            "FCS error pakets."
    ::= { slot11ModuleIfEntry 16 }

slot11ModuleifInUnknownProtos OBJECT-TYPE
    SYNTAX      Counter64
    MAX-ACCESS  read-only
    STATUS      current
    DESCRIPTION
            "For packet-oriented interfaces, the number of packets
            received via the interface which were discarded because of
            an unknown or unsupported protocol.  For character-oriented
            or fixed-length interfaces that support protocol
            multiplexing the number of transmission units received via
            the interface which were discarded because of an unknown or
            unsupported protocol.  For any interface that does not
            support protocol multiplexing, this counter will always be
            0.

            Discontinuities in the value of this counter can occur at
            re-initialization of the management system, and at other
            times as indicated by the value of
            ifCounterDiscontinuityTime."
    ::= { slot11ModuleIfEntry 17 }

slot11ModuleifOutOctets OBJECT-TYPE
    SYNTAX      Counter64
    MAX-ACCESS  read-only
    STATUS      current
    DESCRIPTION
            "The total number of octets transmitted out of the
            interface, including framing characters.

            Discontinuities in the value of this counter can occur at
            re-initialization of the management system, and at other
            times as indicated by the value of
            ifCounterDiscontinuityTime."
    ::= { slot11ModuleIfEntry 18 }

slot11ModuleifOutUcastPkts OBJECT-TYPE
    SYNTAX      Counter64
    MAX-ACCESS  read-only
    STATUS      current
    DESCRIPTION
            "The total number of packets that higher-level protocols
            requested be transmitted, and which were not addressed to a
            multicast or broadcast address at this sub-layer, including
            those that were discarded or not sent.

            Discontinuities in the value of this counter can occur at
            re-initialization of the management system, and at other
            times as indicated by the value of
            ifCounterDiscontinuityTime."
    ::= { slot11ModuleIfEntry 19 }

slot11ModuleifOutNUcastPkts OBJECT-TYPE
    SYNTAX      Counter64
    MAX-ACCESS  read-only
    STATUS      deprecated
    DESCRIPTION
            "The total number of packets that higher-level protocols
            requested be transmitted, and which were addressed to a
            multicast or broadcast address at this sub-layer, including
            those that were discarded or not sent.

            Discontinuities in the value of this counter can occur at
            re-initialization of the management system, and at other
            times as indicated by the value of
            ifCounterDiscontinuityTime.

            This object is deprecated in favour of ifOutMulticastPkts
            and ifOutBroadcastPkts."
    ::= { slot11ModuleIfEntry 20 }

slot11ModuleifOutDiscards OBJECT-TYPE
    SYNTAX      Counter64
    MAX-ACCESS  read-only
    STATUS      current
    DESCRIPTION
            "The number of outbound packets which were chosen to be
            discarded even though no errors had been detected to prevent
            their being transmitted.  One possible reason for discarding
            such a packet could be to free up buffer space.

            Discontinuities in the value of this counter can occur at
            re-initialization of the management system, and at other
            times as indicated by the value of
            ifCounterDiscontinuityTime."
    ::= { slot11ModuleIfEntry 21 }

slot11ModuleifOutErrors OBJECT-TYPE
    SYNTAX      Counter64
    MAX-ACCESS  read-only
    STATUS      current
    DESCRIPTION
            "For packet-oriented interfaces, the number of outbound
            packets that could not be transmitted because of errors.
            For character-oriented or fixed-length interfaces, the
            number of outbound transmission units that could not be
            transmitted because of errors.

            Discontinuities in the value of this counter can occur at
            re-initialization of the management system, and at other
            times as indicated by the value of
            ifCounterDiscontinuityTime."
    ::= { slot11ModuleIfEntry 22 }

slot11ModuleifOutFcsErrorPkts OBJECT-TYPE
    SYNTAX      Counter64
    MAX-ACCESS  read-only
    STATUS      current
    DESCRIPTION
            "FCS error pakets."
    ::= { slot11ModuleIfEntry 23 }

slot11ModuleifOutQLen OBJECT-TYPE
    SYNTAX      Gauge32
    MAX-ACCESS  read-only
    STATUS      deprecated
    DESCRIPTION
            "The length of the output packet queue (in packets)."
    ::= { slot11ModuleIfEntry 24 }

slot11ModuleifOutOctetsRate OBJECT-TYPE
    SYNTAX      Counter64
    MAX-ACCESS  read-only
    STATUS      current
    DESCRIPTION
            "The speed of octets trans on the interface(kbps)"
    ::= { slot11ModuleIfEntry 25 }

slot11ModuleifInOctetsRate OBJECT-TYPE
    SYNTAX      Counter64
    MAX-ACCESS  read-only
    STATUS      current
    DESCRIPTION
            "The speed of octets received on the interface(kbps)"
    ::= { slot11ModuleIfEntry 26 }

slot11ModuleifOutPktsRate OBJECT-TYPE
    SYNTAX      Counter64
    MAX-ACCESS  read-only
    STATUS      current
    DESCRIPTION
            "The speed of packets trans on the interface(pps)"
    ::= { slot11ModuleIfEntry 27 }

slot11ModuleifInPktsRate OBJECT-TYPE
    SYNTAX      Counter64
    MAX-ACCESS  read-only
    STATUS      current
    DESCRIPTION
            "The speed of octets received on the interface(kbps)"
    ::= { slot11ModuleIfEntry 28 }

slot11ModuleifRxPower OBJECT-TYPE
    SYNTAX      DisplayString (SIZE (0..255))
    MAX-ACCESS  read-only
    STATUS      current
    DESCRIPTION
            "the value of interface's received power, in dbm format."
    ::= { slot11ModuleIfEntry 29 }

slot11ModuleifTxPower OBJECT-TYPE
    SYNTAX      DisplayString (SIZE (0..255))
    MAX-ACCESS  read-only
    STATUS      current
    DESCRIPTION
            "the value of interface's send power, in dbm format."
    ::= { slot11ModuleIfEntry 30 }

slot11ModuleifSpecific OBJECT-TYPE
    SYNTAX      OBJECT IDENTIFIER
    MAX-ACCESS  read-only
    STATUS      deprecated
    DESCRIPTION
            "A reference to MIB definitions specific to the particular
            media being used to realize the interface.  It is

            recommended that this value point to an instance of a MIB
            object in the media-specific MIB, i.e., that this object
            have the semantics associated with the InstancePointer
            textual convention defined in RFC 2579.  In fact, it is
            recommended that the media-specific MIB specify what value
            ifSpecific should/can take for values of ifType.  If no MIB
            definitions specific to the particular media are available,
            the value should be set to the OBJECT IDENTIFIER { 0 0 }."
    ::= { slot11ModuleIfEntry 31 }  
   
slot11ModuleifTxMirrorList OBJECT-TYPE
    SYNTAX      DisplayString (SIZE (0..255))
    MAX-ACCESS  read-only
    STATUS      deprecated
    DESCRIPTION
            "the interface tx mirror list."
    ::= { slot11ModuleIfEntry 32 }  
 
slot11ModuleifRxMirrorList OBJECT-TYPE
    SYNTAX      DisplayString (SIZE (0..255))
    MAX-ACCESS  read-only
    STATUS      deprecated
    DESCRIPTION
            "the interface rx mirror list."
    ::= { slot11ModuleIfEntry 33 }  

slot11ModuleifRxPowerMin OBJECT-TYPE
    SYNTAX      DisplayString (SIZE (0..255))
    MAX-ACCESS  read-only
    STATUS      deprecated
    DESCRIPTION
            "the interface min rx power."
    ::= { slot11ModuleIfEntry 34 }  

slot11ModuleifRxPowerMax OBJECT-TYPE
    SYNTAX      DisplayString (SIZE (0..255))
    MAX-ACCESS  read-only
    STATUS      deprecated
    DESCRIPTION
            "the interface max rx power."
    ::= { slot11ModuleIfEntry 35 }  

slot11ModuleifTxPowerMin OBJECT-TYPE
    SYNTAX      DisplayString (SIZE (0..255))
    MAX-ACCESS  read-only
    STATUS      deprecated
    DESCRIPTION
            "the interface min tx power."
    ::= { slot11ModuleIfEntry 36 }  

slot11ModuleifTxPowerMax OBJECT-TYPE
    SYNTAX      DisplayString (SIZE (0..255))
    MAX-ACCESS  read-only
    STATUS      deprecated
    DESCRIPTION
            "the interface max tx power."
    ::= { slot11ModuleIfEntry 37 }  

slot11ModuleifRxHisPeak OBJECT-TYPE
    SYNTAX      Counter64
    MAX-ACCESS  read-only
    STATUS      current
    DESCRIPTION
            "The max speed of rx rate on the interface(kbps)"
    ::= { slot11ModuleIfEntry 38 }

slot11ModuleifTxHisPeak OBJECT-TYPE
    SYNTAX      Counter64
    MAX-ACCESS  read-only
    STATUS      current
    DESCRIPTION
            "The max speed of tx rate on the interface(kbps)"
    ::= { slot11ModuleIfEntry 39 }

slot11ModuleifMode OBJECT-TYPE
    SYNTAX      DisplayString (SIZE (0..255))
    MAX-ACCESS  read-only
    STATUS      deprecated
    DESCRIPTION
            "the interface if mode."
    ::= { slot11ModuleIfEntry 40 }  

   
-- slot 12 --

-- slot12Table --

slot12Table OBJECT-TYPE
    SYNTAX      SEQUENCE OF Slot12Entry
    MAX-ACCESS  not-accessible
    STATUS      current
    DESCRIPTION
            "A list of all slot12Type's utilization."
    ::= { slot12 1 }  

slot12Entry OBJECT-TYPE
    SYNTAX      Slot12Entry
    MAX-ACCESS  not-accessible
    STATUS      current
    DESCRIPTION
            "An entry contains a slot12's utilization."
    INDEX   { slot12Index }
    ::= { slot12Table 1 }

Slot12Entry ::=
    SEQUENCE {     
		slot12Index                       Integer32,
		slot12Type                        DisplayString,
		slot12Status                      DisplayString,		
        slot12SerialNumber                DisplayString,		
        slot12Temperature                 DisplayString
    }  

slot12Index OBJECT-TYPE
    SYNTAX      Integer32 (1..2147483647)
    MAX-ACCESS  not-accessible
    STATUS      current
    DESCRIPTION
            "A unique value, greater than zero, for each chassis`s slot12."
    ::= { slot12Entry 1 }

slot12Type OBJECT-TYPE
    SYNTAX      DisplayString (SIZE (0..255))
    MAX-ACCESS  read-only
    STATUS      current
    DESCRIPTION
            "the slot12Type of each chassis."
    ::= { slot12Entry 2 }

slot12Status OBJECT-TYPE
    SYNTAX      DisplayString (SIZE (0..255))
    MAX-ACCESS  read-only
    STATUS      current
    DESCRIPTION
            "A string to describe the board status." 
    ::= { slot12Entry 3 }   

slot12SerialNumber OBJECT-TYPE
    SYNTAX      DisplayString (SIZE (0..255))
    MAX-ACCESS  read-only
    STATUS      current
    DESCRIPTION
            "A string to describe the board serial number." 
    ::= { slot12Entry 4 }   

slot12Temperature OBJECT-TYPE
    SYNTAX      DisplayString (SIZE (0..255))
    MAX-ACCESS  read-only
    STATUS      current
    DESCRIPTION
            "A string to describe the board temperature." 
    ::= { slot12Entry 5 }   


slot12Module OBJECT IDENTIFIER ::= { slot12 2 }

-- slot12ModuleTable --
slot12ModuleTable OBJECT-TYPE
    SYNTAX      SEQUENCE OF Slot12ModuleEntry
    MAX-ACCESS  not-accessible
    STATUS      current
    DESCRIPTION
            "A list of all slot12Module's utilization."
    ::= { slot12Module 1 }  

slot12ModuleEntry OBJECT-TYPE
    SYNTAX      Slot12ModuleEntry
    MAX-ACCESS  not-accessible
    STATUS      current
    DESCRIPTION
            "An entry contains a slot12Module's utilization."
    INDEX   { slot12ModuleIndex }
    ::= { slot12ModuleTable 1 }

Slot12ModuleEntry ::=
    SEQUENCE {     
		slot12ModuleIndex                       Integer32,
		slot12ModuleId                           DisplayString,  
		slot12ModuleIfNumber                     Integer32		
    } 

slot12ModuleIndex OBJECT-TYPE
    SYNTAX      Integer32 (1..2147483647)
    MAX-ACCESS  not-accessible
    STATUS      current
    DESCRIPTION
            "A unique value, greater than zero, for each chassis`s slot12."
    ::= { slot12ModuleEntry 1 }

slot12ModuleId OBJECT-TYPE
    SYNTAX      DisplayString (SIZE (0..32))
    MAX-ACCESS  read-only
    STATUS      current
    DESCRIPTION
            "the value of module`s id"
    ::= { slot12ModuleEntry 2 }
  
slot12ModuleIfNumber OBJECT-TYPE
    SYNTAX      Integer32(0..2147483647)
    MAX-ACCESS  read-only
    STATUS      current
    DESCRIPTION
            "The number of network interfaces (regardless of their
            current state) present on this system." 
    ::= { slot12ModuleEntry 3 } 
    
slot12ModuleIfTable OBJECT-TYPE
    SYNTAX      SEQUENCE OF Slot12ModuleIfEntry
    MAX-ACCESS  not-accessible
    STATUS      current
    DESCRIPTION
            "A list of interface entries.  The number of entries is
            given by the value of ifNumber."
    ::= { slot12Module 2 } 
    
slot12ModuleIfEntry OBJECT-TYPE
    SYNTAX      Slot12ModuleIfEntry
    MAX-ACCESS  not-accessible
    STATUS      current
    DESCRIPTION
            "An entry containing management information applicable to a
            particular interface."
    INDEX   { slot12ModuleifIndex }
    ::= { slot12ModuleIfTable 1 }
    
Slot12ModuleIfEntry ::=
    SEQUENCE {
        slot12ModuleifIndex                 InterfaceIndex,  
        slot12ModuleIfId                    DisplayString,  
        slot12ModuleifDescr                 DisplayString,           
        slot12ModuleifType                  IANAifType,   		
        slot12ModuleifMtu                   Integer32,                
        slot12ModuleifSpeed                 Counter64,               
        slot12ModuleifPhysAddress           PhysAddress,              
        slot12ModuleifAdminStatus           INTEGER,                  
        slot12ModuleifOperStatus            INTEGER,                  
        slot12ModuleifLastChange            TimeTicks,                
        slot12ModuleifInOctets              Counter64,                
        slot12ModuleifInUcastPkts           Counter64,                
        slot12ModuleifInNUcastPkts          Counter64,   
        slot12ModuleifInDiscards            Counter64,
        slot12ModuleifInErrors              Counter64,
        slot12ModuleifInFcsErrorPkts        Counter64,
        slot12ModuleifInUnknownProtos       Counter64,	-- deprecated
        slot12ModuleifOutOctets             Counter64,
        slot12ModuleifOutUcastPkts          Counter64,
        slot12ModuleifOutNUcastPkts         Counter64,  -- deprecated
        slot12ModuleifOutDiscards           Counter64,
        slot12ModuleifOutErrors             Counter64,
        slot12ModuleifOutFcsErrorPkts       Counter64,
        slot12ModuleifOutQLen               Gauge32,    -- deprecated  
        slot12ModuleifOutOctetsRate         Counter64,
        slot12ModuleifInOctetsRate          Counter64,
        slot12ModuleifOutPktsRate           Counter64,
        slot12ModuleifInPktsRate            Counter64,
        slot12ModuleifRxPower               DisplayString,
        slot12ModuleifTxPower               DisplayString,
        slot12ModuleifSpecific              OBJECT IDENTIFIER,
        slot12ModuleifTxMirrorList          DisplayString,
        slot12ModuleifRxMirrorList          DisplayString,
        slot12ModuleifRxPowerMin               DisplayString,
        slot12ModuleifRxPowerMax               DisplayString,
        slot12ModuleifTxPowerMin               DisplayString,
        slot12ModuleifTxPowerMax               DisplayString,
        slot12ModuleifRxHisPeak            Counter64,
        slot12ModuleifTxHisPeak            Counter64,
        slot12ModuleifMode                 DisplayString   		
    }         

slot12ModuleifIndex OBJECT-TYPE
    SYNTAX      InterfaceIndex
    MAX-ACCESS  read-only
    STATUS      current
    DESCRIPTION
            "A unique value, greater than zero, for each interface.  It
            is recommended that values are assigned contiguously
            starting from 1.  The value for each interface sub-layer
            must remain constant at least from one re-initialization of
            the entity's network management system to the next re-
            initialization."
    ::= { slot12ModuleIfEntry 1 }
    
slot12ModuleIfId OBJECT-TYPE
    SYNTAX      DisplayString (SIZE (0..32))
    MAX-ACCESS  read-only
    STATUS      current
    DESCRIPTION
            "the value of module`s id"
    ::= { slot12ModuleIfEntry 2 }
    
slot12ModuleifDescr OBJECT-TYPE
    SYNTAX      DisplayString (SIZE (0..255))
    MAX-ACCESS  read-only
    STATUS      current
    DESCRIPTION
            "A textual string containing information about the
            interface.  This string should include the name of the
            manufacturer, the product name and the version of the
            interface hardware/software."
    ::= { slot12ModuleIfEntry 3 }
    
slot12ModuleifType OBJECT-TYPE
    SYNTAX      IANAifType
    MAX-ACCESS  read-only
    STATUS      current
    DESCRIPTION
            "The type of interface.  Additional values for ifType are
            assigned by the Internet Assigned Numbers Authority (IANA),
            through updating the syntax of the IANAifType textual
            convention."
    ::= { slot12ModuleIfEntry 4 }

slot12ModuleifMtu OBJECT-TYPE
    SYNTAX      Integer32(1..2147483647)
    MAX-ACCESS  read-only
    STATUS      current
    DESCRIPTION
            "The size of the largest packet which can be sent/received
            on the interface, specified in octets.  For interfaces that
            are used for transmitting network datagrams, this is the
            size of the largest network datagram that can be sent on the
            interface."
    ::= { slot12ModuleIfEntry 5 }

slot12ModuleifSpeed OBJECT-TYPE
    SYNTAX      Counter64
    MAX-ACCESS  read-only
    STATUS      current
    DESCRIPTION
            "An estimate of the interface's current bandwidth in bits
            per second.  For interfaces which do not vary in bandwidth
            or for those where no accurate estimation can be made, this
            object should contain the nominal bandwidth. For a sub-layer
            which has no concept of bandwidth, this object should be zero."
    ::= { slot12ModuleIfEntry 6 }

slot12ModuleifPhysAddress OBJECT-TYPE
    SYNTAX      PhysAddress
    MAX-ACCESS  read-only
    STATUS      current
    DESCRIPTION
            "The interface's address at its protocol sub-layer.  For
            example, for an 802.x interface, this object normally
            contains a MAC address.  The interface's media-specific MIB
            must define the bit and byte ordering and the format of the
            value of this object.  For interfaces which do not have such
            an address (e.g., a serial line), this object should contain
            an octet string of zero length."
    ::= { slot12ModuleIfEntry 7 }
    
slot12ModuleifAdminStatus OBJECT-TYPE
    SYNTAX  INTEGER {
                up(1),       -- ready to pass packets
                down(2),
                testing(3)   -- in some test mode
            }
    MAX-ACCESS  read-write
    STATUS      current
    DESCRIPTION
            "The desired state of the interface.  The testing(3) state
            indicates that no operational packets can be passed.  When a
            managed system initializes, all interfaces start with
            ifAdminStatus in the down(2) state.  As a result of either
            explicit management action or per configuration information
            retained by the managed system, ifAdminStatus is then
            changed to either the up(1) or testing(3) states (or remains
            in the down(2) state)."
    ::= { slot12ModuleIfEntry 8 }

slot12ModuleifOperStatus OBJECT-TYPE
    SYNTAX  INTEGER {
                up(1),        -- ready to pass packets
                down(2),
                testing(3),   -- in some test mode
                unknown(4),   -- status can not be determined
                              -- for some reason.
                dormant(5),
                notPresent(6),    -- some component is missing
                lowerLayerDown(7) -- down due to state of
                                  -- lower-layer interface(s)
            }
    MAX-ACCESS  read-only
    STATUS      current
    DESCRIPTION
            "The current operational state of the interface.  The
            testing(3) state indicates that no operational packets can
            be passed.  If ifAdminStatus is down(2) then ifOperStatus
            should be down(2).  If ifAdminStatus is changed to up(1)
            then ifOperStatus should change to up(1) if the interface is
            ready to transmit and receive network traffic; it should
            change to dormant(5) if the interface is waiting for
            external actions (such as a serial line waiting for an
            incoming connection); it should remain in the down(2) state
            if and only if there is a fault that prevents it from going
            to the up(1) state; it should remain in the notPresent(6)
            state if the interface has missing (typically, hardware)
            components."
    ::= { slot12ModuleIfEntry 9 }

slot12ModuleifLastChange OBJECT-TYPE
    SYNTAX      TimeTicks
    MAX-ACCESS  read-only
    STATUS      current
    DESCRIPTION
            "The value of sysUpTime at the time the interface entered
            its current operational state.  If the current state was
            entered prior to the last re-initialization of the local
            network management subsystem, then this object contains a
            zero value."
    ::= { slot12ModuleIfEntry 10 }

slot12ModuleifInOctets OBJECT-TYPE
    SYNTAX      Counter64
    MAX-ACCESS  read-only
    STATUS      current
    DESCRIPTION
            "The total number of octets received on the interface,
            including framing characters.

            Discontinuities in the value of this counter can occur at
            re-initialization of the management system, and at other
            times as indicated by the value of
            ifCounterDiscontinuityTime."
    ::= { slot12ModuleIfEntry 11 }

slot12ModuleifInUcastPkts OBJECT-TYPE
    SYNTAX      Counter64
    MAX-ACCESS  read-only
    STATUS      current
    DESCRIPTION
            "The number of packets, delivered by this sub-layer to a
            higher (sub-)layer, which were not addressed to a multicast
            or broadcast address at this sub-layer.

            Discontinuities in the value of this counter can occur at
            re-initialization of the management system, and at other
            times as indicated by the value of
            ifCounterDiscontinuityTime."
    ::= { slot12ModuleIfEntry 12 }

slot12ModuleifInNUcastPkts OBJECT-TYPE
    SYNTAX  Counter64
    MAX-ACCESS  read-only
    STATUS      current
    DESCRIPTION
            "The number of packets, delivered by this sub-layer to a
            higher (sub-)layer, which were addressed to a multicast or
            broadcast address at this sub-layer.

            Discontinuities in the value of this counter can occur at
            re-initialization of the management system, and at other
            times as indicated by the value of
            ifCounterDiscontinuityTime.

            This object is deprecated in favour of ifInMulticastPkts and
            ifInBroadcastPkts."
    ::= { slot12ModuleIfEntry 13 }

slot12ModuleifInDiscards OBJECT-TYPE
    SYNTAX      Counter64
    MAX-ACCESS  read-only
    STATUS      current
    DESCRIPTION
            "The number of inbound packets which were chosen to be
            discarded even though no errors had been detected to prevent

            their being deliverable to a higher-layer protocol.  One
            possible reason for discarding such a packet could be to
            free up buffer space.

            Discontinuities in the value of this counter can occur at
            re-initialization of the management system, and at other
            times as indicated by the value of
            ifCounterDiscontinuityTime."
    ::= { slot12ModuleIfEntry 14 }

slot12ModuleifInErrors OBJECT-TYPE
    SYNTAX      Counter64
    MAX-ACCESS  read-only
    STATUS      current
    DESCRIPTION
            "For packet-oriented interfaces, the number of inbound
            packets that contained errors preventing them from being
            deliverable to a higher-layer protocol.  For character-
            oriented or fixed-length interfaces, the number of inbound
            transmission units that contained errors preventing them
            from being deliverable to a higher-layer protocol.

            Discontinuities in the value of this counter can occur at
            re-initialization of the management system, and at other
            times as indicated by the value of
            ifCounterDiscontinuityTime."
    ::= { slot12ModuleIfEntry 15 }

slot12ModuleifInFcsErrorPkts OBJECT-TYPE
    SYNTAX      Counter64
    MAX-ACCESS  read-only
    STATUS      current
    DESCRIPTION
            "FCS error pakets."
    ::= { slot12ModuleIfEntry 16 }

slot12ModuleifInUnknownProtos OBJECT-TYPE
    SYNTAX      Counter64
    MAX-ACCESS  read-only
    STATUS      current
    DESCRIPTION
            "For packet-oriented interfaces, the number of packets
            received via the interface which were discarded because of
            an unknown or unsupported protocol.  For character-oriented
            or fixed-length interfaces that support protocol
            multiplexing the number of transmission units received via
            the interface which were discarded because of an unknown or
            unsupported protocol.  For any interface that does not
            support protocol multiplexing, this counter will always be
            0.

            Discontinuities in the value of this counter can occur at
            re-initialization of the management system, and at other
            times as indicated by the value of
            ifCounterDiscontinuityTime."
    ::= { slot12ModuleIfEntry 17 }

slot12ModuleifOutOctets OBJECT-TYPE
    SYNTAX      Counter64
    MAX-ACCESS  read-only
    STATUS      current
    DESCRIPTION
            "The total number of octets transmitted out of the
            interface, including framing characters.

            Discontinuities in the value of this counter can occur at
            re-initialization of the management system, and at other
            times as indicated by the value of
            ifCounterDiscontinuityTime."
    ::= { slot12ModuleIfEntry 18 }

slot12ModuleifOutUcastPkts OBJECT-TYPE
    SYNTAX      Counter64
    MAX-ACCESS  read-only
    STATUS      current
    DESCRIPTION
            "The total number of packets that higher-level protocols
            requested be transmitted, and which were not addressed to a
            multicast or broadcast address at this sub-layer, including
            those that were discarded or not sent.

            Discontinuities in the value of this counter can occur at
            re-initialization of the management system, and at other
            times as indicated by the value of
            ifCounterDiscontinuityTime."
    ::= { slot12ModuleIfEntry 19 }

slot12ModuleifOutNUcastPkts OBJECT-TYPE
    SYNTAX      Counter64
    MAX-ACCESS  read-only
    STATUS      deprecated
    DESCRIPTION
            "The total number of packets that higher-level protocols
            requested be transmitted, and which were addressed to a
            multicast or broadcast address at this sub-layer, including
            those that were discarded or not sent.

            Discontinuities in the value of this counter can occur at
            re-initialization of the management system, and at other
            times as indicated by the value of
            ifCounterDiscontinuityTime.

            This object is deprecated in favour of ifOutMulticastPkts
            and ifOutBroadcastPkts."
    ::= { slot12ModuleIfEntry 20 }

slot12ModuleifOutDiscards OBJECT-TYPE
    SYNTAX      Counter64
    MAX-ACCESS  read-only
    STATUS      current
    DESCRIPTION
            "The number of outbound packets which were chosen to be
            discarded even though no errors had been detected to prevent
            their being transmitted.  One possible reason for discarding
            such a packet could be to free up buffer space.

            Discontinuities in the value of this counter can occur at
            re-initialization of the management system, and at other
            times as indicated by the value of
            ifCounterDiscontinuityTime."
    ::= { slot12ModuleIfEntry 21 }

slot12ModuleifOutErrors OBJECT-TYPE
    SYNTAX      Counter64
    MAX-ACCESS  read-only
    STATUS      current
    DESCRIPTION
            "For packet-oriented interfaces, the number of outbound
            packets that could not be transmitted because of errors.
            For character-oriented or fixed-length interfaces, the
            number of outbound transmission units that could not be
            transmitted because of errors.

            Discontinuities in the value of this counter can occur at
            re-initialization of the management system, and at other
            times as indicated by the value of
            ifCounterDiscontinuityTime."
    ::= { slot12ModuleIfEntry 22 }

slot12ModuleifOutFcsErrorPkts OBJECT-TYPE
    SYNTAX      Counter64
    MAX-ACCESS  read-only
    STATUS      current
    DESCRIPTION
            "FCS error pakets."
    ::= { slot12ModuleIfEntry 23 }

slot12ModuleifOutQLen OBJECT-TYPE
    SYNTAX      Gauge32
    MAX-ACCESS  read-only
    STATUS      deprecated
    DESCRIPTION
            "The length of the output packet queue (in packets)."
    ::= { slot12ModuleIfEntry 24 }

slot12ModuleifOutOctetsRate OBJECT-TYPE
    SYNTAX      Counter64
    MAX-ACCESS  read-only
    STATUS      current
    DESCRIPTION
            "The speed of octets trans on the interface(kbps)"
    ::= { slot12ModuleIfEntry 25 }

slot12ModuleifInOctetsRate OBJECT-TYPE
    SYNTAX      Counter64
    MAX-ACCESS  read-only
    STATUS      current
    DESCRIPTION
            "The speed of octets received on the interface(kbps)"
    ::= { slot12ModuleIfEntry 26 }

slot12ModuleifOutPktsRate OBJECT-TYPE
    SYNTAX      Counter64
    MAX-ACCESS  read-only
    STATUS      current
    DESCRIPTION
            "The speed of packets trans on the interface(pps)"
    ::= { slot12ModuleIfEntry 27 }

slot12ModuleifInPktsRate OBJECT-TYPE
    SYNTAX      Counter64
    MAX-ACCESS  read-only
    STATUS      current
    DESCRIPTION
            "The speed of octets received on the interface(kbps)"
    ::= { slot12ModuleIfEntry 28 }

slot12ModuleifRxPower OBJECT-TYPE
    SYNTAX      DisplayString (SIZE (0..255))
    MAX-ACCESS  read-only
    STATUS      current
    DESCRIPTION
            "the value of interface's received power, in dbm format."
    ::= { slot12ModuleIfEntry 29 }

slot12ModuleifTxPower OBJECT-TYPE
    SYNTAX      DisplayString (SIZE (0..255))
    MAX-ACCESS  read-only
    STATUS      current
    DESCRIPTION
            "the value of interface's send power, in dbm format."
    ::= { slot12ModuleIfEntry 30 }

slot12ModuleifSpecific OBJECT-TYPE
    SYNTAX      OBJECT IDENTIFIER
    MAX-ACCESS  read-only
    STATUS      deprecated
    DESCRIPTION
            "A reference to MIB definitions specific to the particular
            media being used to realize the interface.  It is

            recommended that this value point to an instance of a MIB
            object in the media-specific MIB, i.e., that this object
            have the semantics associated with the InstancePointer
            textual convention defined in RFC 2579.  In fact, it is
            recommended that the media-specific MIB specify what value
            ifSpecific should/can take for values of ifType.  If no MIB
            definitions specific to the particular media are available,
            the value should be set to the OBJECT IDENTIFIER { 0 0 }."
    ::= { slot12ModuleIfEntry 31 }  
   
slot12ModuleifTxMirrorList OBJECT-TYPE
    SYNTAX      DisplayString (SIZE (0..255))
    MAX-ACCESS  read-only
    STATUS      deprecated
    DESCRIPTION
            "the interface tx mirror list."
    ::= { slot12ModuleIfEntry 32 }  
 
slot12ModuleifRxMirrorList OBJECT-TYPE
    SYNTAX      DisplayString (SIZE (0..255))
    MAX-ACCESS  read-only
    STATUS      deprecated
    DESCRIPTION
            "the interface rx mirror list."
    ::= { slot12ModuleIfEntry 33 }  
  
slot12ModuleifRxPowerMin OBJECT-TYPE
    SYNTAX      DisplayString (SIZE (0..255))
    MAX-ACCESS  read-only
    STATUS      deprecated
    DESCRIPTION
            "the interface min rx power."
    ::= { slot12ModuleIfEntry 34 }  

slot12ModuleifRxPowerMax OBJECT-TYPE
    SYNTAX      DisplayString (SIZE (0..255))
    MAX-ACCESS  read-only
    STATUS      deprecated
    DESCRIPTION
            "the interface max rx power."
    ::= { slot12ModuleIfEntry 35 }  

slot12ModuleifTxPowerMin OBJECT-TYPE
    SYNTAX      DisplayString (SIZE (0..255))
    MAX-ACCESS  read-only
    STATUS      deprecated
    DESCRIPTION
            "the interface min tx power."
    ::= { slot12ModuleIfEntry 36 }  

slot12ModuleifTxPowerMax OBJECT-TYPE
    SYNTAX      DisplayString (SIZE (0..255))
    MAX-ACCESS  read-only
    STATUS      deprecated
    DESCRIPTION
            "the interface max tx power."
    ::= { slot12ModuleIfEntry 37 }  

slot12ModuleifRxHisPeak OBJECT-TYPE
    SYNTAX      Counter64
    MAX-ACCESS  read-only
    STATUS      current
    DESCRIPTION
            "The max speed of rx rate on the interface(kbps)"
    ::= { slot12ModuleIfEntry 38 }

slot12ModuleifTxHisPeak OBJECT-TYPE
    SYNTAX      Counter64
    MAX-ACCESS  read-only
    STATUS      current
    DESCRIPTION
            "The max speed of tx rate on the interface(kbps)"
    ::= { slot12ModuleIfEntry 39 }

slot12ModuleifMode OBJECT-TYPE
    SYNTAX      DisplayString (SIZE (0..255))
    MAX-ACCESS  read-only
    STATUS      deprecated
    DESCRIPTION
            "the interface if mode."
    ::= { slot12ModuleIfEntry 40 }  

-- slot 13 --

-- slot13Table --

slot13Table OBJECT-TYPE
    SYNTAX      SEQUENCE OF Slot13Entry
    MAX-ACCESS  not-accessible
    STATUS      current
    DESCRIPTION
            "A list of all slot13Type's utilization."
    ::= { slot13 1 }  

slot13Entry OBJECT-TYPE
    SYNTAX      Slot13Entry
    MAX-ACCESS  not-accessible
    STATUS      current
    DESCRIPTION
            "An entry contains a slot13's utilization."
    INDEX   { slot13Index }
    ::= { slot13Table 1 }

Slot13Entry ::=
    SEQUENCE {     
		slot13Index                       Integer32,
		slot13Type                        DisplayString,
		slot13Status                      DisplayString,		
        slot13SerialNumber                DisplayString,		
        slot13Temperature                 DisplayString
    }  

slot13Index OBJECT-TYPE
    SYNTAX      Integer32 (1..2147483647)
    MAX-ACCESS  not-accessible
    STATUS      current
    DESCRIPTION
            "A unique value, greater than zero, for each chassis`s slot13."
    ::= { slot13Entry 1 }

slot13Type OBJECT-TYPE
    SYNTAX      DisplayString (SIZE (0..255))
    MAX-ACCESS  read-only
    STATUS      current
    DESCRIPTION
            "the slot13Type of each chassis."
    ::= { slot13Entry 2 }

slot13Status OBJECT-TYPE
    SYNTAX      DisplayString (SIZE (0..255))
    MAX-ACCESS  read-only
    STATUS      current
    DESCRIPTION
            "A string to describe the board status." 
    ::= { slot13Entry 3 }   

slot13SerialNumber OBJECT-TYPE
    SYNTAX      DisplayString (SIZE (0..255))
    MAX-ACCESS  read-only
    STATUS      current
    DESCRIPTION
            "A string to describe the board serial number." 
    ::= { slot13Entry 4 }   

slot13Temperature OBJECT-TYPE
    SYNTAX      DisplayString (SIZE (0..255))
    MAX-ACCESS  read-only
    STATUS      current
    DESCRIPTION
            "A string to describe the board temperature." 
    ::= { slot13Entry 5 }   


slot13Module OBJECT IDENTIFIER ::= { slot13 2 }

-- slot13ModuleTable --
slot13ModuleTable OBJECT-TYPE
    SYNTAX      SEQUENCE OF Slot13ModuleEntry
    MAX-ACCESS  not-accessible
    STATUS      current
    DESCRIPTION
            "A list of all slot13Module's utilization."
    ::= { slot13Module 1 }  

slot13ModuleEntry OBJECT-TYPE
    SYNTAX      Slot13ModuleEntry
    MAX-ACCESS  not-accessible
    STATUS      current
    DESCRIPTION
            "An entry contains a slot13Module's utilization."
    INDEX   { slot13ModuleIndex }
    ::= { slot13ModuleTable 1 }

Slot13ModuleEntry ::=
    SEQUENCE {     
		slot13ModuleIndex                       Integer32,
		slot13ModuleId                           DisplayString,  
		slot13ModuleIfNumber                     Integer32		
    } 

slot13ModuleIndex OBJECT-TYPE
    SYNTAX      Integer32 (1..2147483647)
    MAX-ACCESS  not-accessible
    STATUS      current
    DESCRIPTION
            "A unique value, greater than zero, for each chassis`s slot13."
    ::= { slot13ModuleEntry 1 }

slot13ModuleId OBJECT-TYPE
    SYNTAX      DisplayString (SIZE (0..32))
    MAX-ACCESS  read-only
    STATUS      current
    DESCRIPTION
            "the value of module`s id"
    ::= { slot13ModuleEntry 2 }
  
slot13ModuleIfNumber OBJECT-TYPE
    SYNTAX      Integer32(0..2147483647)
    MAX-ACCESS  read-only
    STATUS      current
    DESCRIPTION
            "The number of network interfaces (regardless of their
            current state) present on this system." 
    ::= { slot13ModuleEntry 3 } 
    
slot13ModuleIfTable OBJECT-TYPE
    SYNTAX      SEQUENCE OF Slot13ModuleIfEntry
    MAX-ACCESS  not-accessible
    STATUS      current
    DESCRIPTION
            "A list of interface entries.  The number of entries is
            given by the value of ifNumber."
    ::= { slot13Module 2 } 
    
slot13ModuleIfEntry OBJECT-TYPE
    SYNTAX      Slot13ModuleIfEntry
    MAX-ACCESS  not-accessible
    STATUS      current
    DESCRIPTION
            "An entry containing management information applicable to a
            particular interface."
    INDEX   { slot13ModuleifIndex }
    ::= { slot13ModuleIfTable 1 }
    
Slot13ModuleIfEntry ::=
    SEQUENCE {
        slot13ModuleifIndex                 InterfaceIndex,  
        slot13ModuleIfId                    DisplayString,  
        slot13ModuleifDescr                 DisplayString,           
        slot13ModuleifType                  IANAifType,   		
        slot13ModuleifMtu                   Integer32,                
        slot13ModuleifSpeed                 Counter64,               
        slot13ModuleifPhysAddress           PhysAddress,              
        slot13ModuleifAdminStatus           INTEGER,                  
        slot13ModuleifOperStatus            INTEGER,                  
        slot13ModuleifLastChange            TimeTicks,                
        slot13ModuleifInOctets              Counter64,                
        slot13ModuleifInUcastPkts           Counter64,                
        slot13ModuleifInNUcastPkts          Counter64, 
        slot13ModuleifInDiscards            Counter64,
        slot13ModuleifInErrors              Counter64,
        slot13ModuleifInFcsErrorPkts        Counter64,
        slot13ModuleifInUnknownProtos       Counter64,	-- deprecated
        slot13ModuleifOutOctets             Counter64,
        slot13ModuleifOutUcastPkts          Counter64,
        slot13ModuleifOutNUcastPkts         Counter64,  -- deprecated
        slot13ModuleifOutDiscards           Counter64,
        slot13ModuleifOutErrors             Counter64,
        slot13ModuleifOutFcsErrorPkts       Counter64,
        slot13ModuleifOutQLen               Gauge32,    -- deprecated  
        slot13ModuleifOutOctetsRate         Counter64,
        slot13ModuleifInOctetsRate          Counter64,
        slot13ModuleifOutPktsRate           Counter64,
        slot13ModuleifInPktsRate            Counter64,
        slot13ModuleifRxPower               DisplayString,
        slot13ModuleifTxPower               DisplayString,
        slot13ModuleifSpecific              OBJECT IDENTIFIER,
        slot13ModuleifTxMirrorList          DisplayString,
        slot13ModuleifRxMirrorList          DisplayString,
        slot13ModuleifRxPowerMin               DisplayString,
        slot13ModuleifRxPowerMax               DisplayString,
        slot13ModuleifTxPowerMin               DisplayString,
        slot13ModuleifTxPowerMax               DisplayString,
        slot13ModuleifRxHisPeak            Counter64,
        slot13ModuleifTxHisPeak            Counter64,
        slot13ModuleifMode                 DisplayString   		
    }         

slot13ModuleifIndex OBJECT-TYPE
    SYNTAX      InterfaceIndex
    MAX-ACCESS  read-only
    STATUS      current
    DESCRIPTION
            "A unique value, greater than zero, for each interface.  It
            is recommended that values are assigned contiguously
            starting from 1.  The value for each interface sub-layer
            must remain constant at least from one re-initialization of
            the entity's network management system to the next re-
            initialization."
    ::= { slot13ModuleIfEntry 1 }
    
slot13ModuleIfId OBJECT-TYPE
    SYNTAX      DisplayString (SIZE (0..32))
    MAX-ACCESS  read-only
    STATUS      current
    DESCRIPTION
            "the value of module`s id"
    ::= { slot13ModuleIfEntry 2 }
    
slot13ModuleifDescr OBJECT-TYPE
    SYNTAX      DisplayString (SIZE (0..255))
    MAX-ACCESS  read-only
    STATUS      current
    DESCRIPTION
            "A textual string containing information about the
            interface.  This string should include the name of the
            manufacturer, the product name and the version of the
            interface hardware/software."
    ::= { slot13ModuleIfEntry 3 }
    
slot13ModuleifType OBJECT-TYPE
    SYNTAX      IANAifType
    MAX-ACCESS  read-only
    STATUS      current
    DESCRIPTION
            "The type of interface.  Additional values for ifType are
            assigned by the Internet Assigned Numbers Authority (IANA),
            through updating the syntax of the IANAifType textual
            convention."
    ::= { slot13ModuleIfEntry 4 }

slot13ModuleifMtu OBJECT-TYPE
    SYNTAX      Integer32(1..2147483647)
    MAX-ACCESS  read-only
    STATUS      current
    DESCRIPTION
            "The size of the largest packet which can be sent/received
            on the interface, specified in octets.  For interfaces that
            are used for transmitting network datagrams, this is the
            size of the largest network datagram that can be sent on the
            interface."
    ::= { slot13ModuleIfEntry 5 }

slot13ModuleifSpeed OBJECT-TYPE
    SYNTAX      Counter64
    MAX-ACCESS  read-only
    STATUS      current
    DESCRIPTION
            "An estimate of the interface's current bandwidth in bits
            per second.  For interfaces which do not vary in bandwidth
            or for those where no accurate estimation can be made, this
            object should contain the nominal bandwidth. For a sub-layer
            which has no concept of bandwidth, this object should be zero."
    ::= { slot13ModuleIfEntry 6 }

slot13ModuleifPhysAddress OBJECT-TYPE
    SYNTAX      PhysAddress
    MAX-ACCESS  read-only
    STATUS      current
    DESCRIPTION
            "The interface's address at its protocol sub-layer.  For
            example, for an 802.x interface, this object normally
            contains a MAC address.  The interface's media-specific MIB
            must define the bit and byte ordering and the format of the
            value of this object.  For interfaces which do not have such
            an address (e.g., a serial line), this object should contain
            an octet string of zero length."
    ::= { slot13ModuleIfEntry 7 }
    
slot13ModuleifAdminStatus OBJECT-TYPE
    SYNTAX  INTEGER {
                up(1),       -- ready to pass packets
                down(2),
                testing(3)   -- in some test mode
            }
    MAX-ACCESS  read-write
    STATUS      current
    DESCRIPTION
            "The desired state of the interface.  The testing(3) state
            indicates that no operational packets can be passed.  When a
            managed system initializes, all interfaces start with
            ifAdminStatus in the down(2) state.  As a result of either
            explicit management action or per configuration information
            retained by the managed system, ifAdminStatus is then
            changed to either the up(1) or testing(3) states (or remains
            in the down(2) state)."
    ::= { slot13ModuleIfEntry 8 }

slot13ModuleifOperStatus OBJECT-TYPE
    SYNTAX  INTEGER {
                up(1),        -- ready to pass packets
                down(2),
                testing(3),   -- in some test mode
                unknown(4),   -- status can not be determined
                              -- for some reason.
                dormant(5),
                notPresent(6),    -- some component is missing
                lowerLayerDown(7) -- down due to state of
                                  -- lower-layer interface(s)
            }
    MAX-ACCESS  read-only
    STATUS      current
    DESCRIPTION
            "The current operational state of the interface.  The
            testing(3) state indicates that no operational packets can
            be passed.  If ifAdminStatus is down(2) then ifOperStatus
            should be down(2).  If ifAdminStatus is changed to up(1)
            then ifOperStatus should change to up(1) if the interface is
            ready to transmit and receive network traffic; it should
            change to dormant(5) if the interface is waiting for
            external actions (such as a serial line waiting for an
            incoming connection); it should remain in the down(2) state
            if and only if there is a fault that prevents it from going
            to the up(1) state; it should remain in the notPresent(6)
            state if the interface has missing (typically, hardware)
            components."
    ::= { slot13ModuleIfEntry 9 }

slot13ModuleifLastChange OBJECT-TYPE
    SYNTAX      TimeTicks
    MAX-ACCESS  read-only
    STATUS      current
    DESCRIPTION
            "The value of sysUpTime at the time the interface entered
            its current operational state.  If the current state was
            entered prior to the last re-initialization of the local
            network management subsystem, then this object contains a
            zero value."
    ::= { slot13ModuleIfEntry 10 }


slot13ModuleifInOctets OBJECT-TYPE
    SYNTAX      Counter64
    MAX-ACCESS  read-only
    STATUS      current
    DESCRIPTION
            "The total number of octets received on the interface,
            including framing characters.

            Discontinuities in the value of this counter can occur at
            re-initialization of the management system, and at other
            times as indicated by the value of
            ifCounterDiscontinuityTime."
    ::= { slot13ModuleIfEntry 11 }

slot13ModuleifInUcastPkts OBJECT-TYPE
    SYNTAX      Counter64
    MAX-ACCESS  read-only
    STATUS      current
    DESCRIPTION
            "The number of packets, delivered by this sub-layer to a
            higher (sub-)layer, which were not addressed to a multicast
            or broadcast address at this sub-layer.

            Discontinuities in the value of this counter can occur at
            re-initialization of the management system, and at other
            times as indicated by the value of
            ifCounterDiscontinuityTime."
    ::= { slot13ModuleIfEntry 12 }

slot13ModuleifInNUcastPkts OBJECT-TYPE
    SYNTAX  Counter64
    MAX-ACCESS  read-only
    STATUS      current
    DESCRIPTION
            "The number of packets, delivered by this sub-layer to a
            higher (sub-)layer, which were addressed to a multicast or
            broadcast address at this sub-layer.

            Discontinuities in the value of this counter can occur at
            re-initialization of the management system, and at other
            times as indicated by the value of
            ifCounterDiscontinuityTime.

            This object is deprecated in favour of ifInMulticastPkts and
            ifInBroadcastPkts."
    ::= { slot13ModuleIfEntry 13 }

slot13ModuleifInDiscards OBJECT-TYPE
    SYNTAX      Counter64
    MAX-ACCESS  read-only
    STATUS      current
    DESCRIPTION
            "The number of inbound packets which were chosen to be
            discarded even though no errors had been detected to prevent

            their being deliverable to a higher-layer protocol.  One
            possible reason for discarding such a packet could be to
            free up buffer space.

            Discontinuities in the value of this counter can occur at
            re-initialization of the management system, and at other
            times as indicated by the value of
            ifCounterDiscontinuityTime."
    ::= { slot13ModuleIfEntry 14 }

slot13ModuleifInErrors OBJECT-TYPE
    SYNTAX      Counter64
    MAX-ACCESS  read-only
    STATUS      current
    DESCRIPTION
            "For packet-oriented interfaces, the number of inbound
            packets that contained errors preventing them from being
            deliverable to a higher-layer protocol.  For character-
            oriented or fixed-length interfaces, the number of inbound
            transmission units that contained errors preventing them
            from being deliverable to a higher-layer protocol.

            Discontinuities in the value of this counter can occur at
            re-initialization of the management system, and at other
            times as indicated by the value of
            ifCounterDiscontinuityTime."
    ::= { slot13ModuleIfEntry 15 }

slot13ModuleifInFcsErrorPkts OBJECT-TYPE
    SYNTAX      Counter64
    MAX-ACCESS  read-only
    STATUS      current
    DESCRIPTION
            "FCS error pakets."
    ::= { slot13ModuleIfEntry 16 }

slot13ModuleifInUnknownProtos OBJECT-TYPE
    SYNTAX      Counter64
    MAX-ACCESS  read-only
    STATUS      current
    DESCRIPTION
            "For packet-oriented interfaces, the number of packets
            received via the interface which were discarded because of
            an unknown or unsupported protocol.  For character-oriented
            or fixed-length interfaces that support protocol
            multiplexing the number of transmission units received via
            the interface which were discarded because of an unknown or
            unsupported protocol.  For any interface that does not
            support protocol multiplexing, this counter will always be
            0.

            Discontinuities in the value of this counter can occur at
            re-initialization of the management system, and at other
            times as indicated by the value of
            ifCounterDiscontinuityTime."
    ::= { slot13ModuleIfEntry 17 }

slot13ModuleifOutOctets OBJECT-TYPE
    SYNTAX      Counter64
    MAX-ACCESS  read-only
    STATUS      current
    DESCRIPTION
            "The total number of octets transmitted out of the
            interface, including framing characters.

            Discontinuities in the value of this counter can occur at
            re-initialization of the management system, and at other
            times as indicated by the value of
            ifCounterDiscontinuityTime."
    ::= { slot13ModuleIfEntry 18 }

slot13ModuleifOutUcastPkts OBJECT-TYPE
    SYNTAX      Counter64
    MAX-ACCESS  read-only
    STATUS      current
    DESCRIPTION
            "The total number of packets that higher-level protocols
            requested be transmitted, and which were not addressed to a
            multicast or broadcast address at this sub-layer, including
            those that were discarded or not sent.

            Discontinuities in the value of this counter can occur at
            re-initialization of the management system, and at other
            times as indicated by the value of
            ifCounterDiscontinuityTime."
    ::= { slot13ModuleIfEntry 19 }

slot13ModuleifOutNUcastPkts OBJECT-TYPE
    SYNTAX      Counter64
    MAX-ACCESS  read-only
    STATUS      deprecated
    DESCRIPTION
            "The total number of packets that higher-level protocols
            requested be transmitted, and which were addressed to a
            multicast or broadcast address at this sub-layer, including
            those that were discarded or not sent.

            Discontinuities in the value of this counter can occur at
            re-initialization of the management system, and at other
            times as indicated by the value of
            ifCounterDiscontinuityTime.

            This object is deprecated in favour of ifOutMulticastPkts
            and ifOutBroadcastPkts."
    ::= { slot13ModuleIfEntry 20 }

slot13ModuleifOutDiscards OBJECT-TYPE
    SYNTAX      Counter64
    MAX-ACCESS  read-only
    STATUS      current
    DESCRIPTION
            "The number of outbound packets which were chosen to be
            discarded even though no errors had been detected to prevent
            their being transmitted.  One possible reason for discarding
            such a packet could be to free up buffer space.

            Discontinuities in the value of this counter can occur at
            re-initialization of the management system, and at other
            times as indicated by the value of
            ifCounterDiscontinuityTime."
    ::= { slot13ModuleIfEntry 21 }

slot13ModuleifOutErrors OBJECT-TYPE
    SYNTAX      Counter64
    MAX-ACCESS  read-only
    STATUS      current
    DESCRIPTION
            "For packet-oriented interfaces, the number of outbound
            packets that could not be transmitted because of errors.
            For character-oriented or fixed-length interfaces, the
            number of outbound transmission units that could not be
            transmitted because of errors.

            Discontinuities in the value of this counter can occur at
            re-initialization of the management system, and at other
            times as indicated by the value of
            ifCounterDiscontinuityTime."
    ::= { slot13ModuleIfEntry 22 }

slot13ModuleifOutFcsErrorPkts OBJECT-TYPE
    SYNTAX      Counter64
    MAX-ACCESS  read-only
    STATUS      current
    DESCRIPTION
            "FCS error pakets."
    ::= { slot13ModuleIfEntry 23 }

slot13ModuleifOutQLen OBJECT-TYPE
    SYNTAX      Gauge32
    MAX-ACCESS  read-only
    STATUS      deprecated
    DESCRIPTION
            "The length of the output packet queue (in packets)."
    ::= { slot13ModuleIfEntry 24 }

slot13ModuleifOutOctetsRate OBJECT-TYPE
    SYNTAX      Counter64
    MAX-ACCESS  read-only
    STATUS      current
    DESCRIPTION
            "The speed of octets trans on the interface(kbps)"
    ::= { slot13ModuleIfEntry 25 }

slot13ModuleifInOctetsRate OBJECT-TYPE
    SYNTAX      Counter64
    MAX-ACCESS  read-only
    STATUS      current
    DESCRIPTION
            "The speed of octets received on the interface(kbps)"
    ::= { slot13ModuleIfEntry 26 }

slot13ModuleifOutPktsRate OBJECT-TYPE
    SYNTAX      Counter64
    MAX-ACCESS  read-only
    STATUS      current
    DESCRIPTION
            "The speed of packets trans on the interface(pps)"
    ::= { slot13ModuleIfEntry 27 }

slot13ModuleifInPktsRate OBJECT-TYPE
    SYNTAX      Counter64
    MAX-ACCESS  read-only
    STATUS      current
    DESCRIPTION
            "The speed of octets received on the interface(kbps)"
    ::= { slot13ModuleIfEntry 28 }

slot13ModuleifRxPower OBJECT-TYPE
    SYNTAX      DisplayString (SIZE (0..255))
    MAX-ACCESS  read-only
    STATUS      current
    DESCRIPTION
            "the value of interface's received power, in dbm format."
    ::= { slot13ModuleIfEntry 29 }

slot13ModuleifTxPower OBJECT-TYPE
    SYNTAX      DisplayString (SIZE (0..255))
    MAX-ACCESS  read-only
    STATUS      current
    DESCRIPTION
            "the value of interface's send power, in dbm format."
    ::= { slot13ModuleIfEntry 30 }

slot13ModuleifSpecific OBJECT-TYPE
    SYNTAX      OBJECT IDENTIFIER
    MAX-ACCESS  read-only
    STATUS      deprecated
    DESCRIPTION
            "A reference to MIB definitions specific to the particular
            media being used to realize the interface.  It is

            recommended that this value point to an instance of a MIB
            object in the media-specific MIB, i.e., that this object
            have the semantics associated with the InstancePointer
            textual convention defined in RFC 2579.  In fact, it is
            recommended that the media-specific MIB specify what value
            ifSpecific should/can take for values of ifType.  If no MIB
            definitions specific to the particular media are available,
            the value should be set to the OBJECT IDENTIFIER { 0 0 }."
    ::= { slot13ModuleIfEntry 31 }  
   
slot13ModuleifTxMirrorList OBJECT-TYPE
    SYNTAX      DisplayString (SIZE (0..255))
    MAX-ACCESS  read-only
    STATUS      deprecated
    DESCRIPTION
            "the interface tx mirror list."
    ::= { slot13ModuleIfEntry 32 }  
 
slot13ModuleifRxMirrorList OBJECT-TYPE
    SYNTAX      DisplayString (SIZE (0..255))
    MAX-ACCESS  read-only
    STATUS      deprecated
    DESCRIPTION
            "the interface rx mirror list."
    ::= { slot13ModuleIfEntry 33 }  
  
slot13ModuleifRxPowerMin OBJECT-TYPE
    SYNTAX      DisplayString (SIZE (0..255))
    MAX-ACCESS  read-only
    STATUS      deprecated
    DESCRIPTION
            "the interface min rx power."
    ::= { slot13ModuleIfEntry 34 }  

slot13ModuleifRxPowerMax OBJECT-TYPE
    SYNTAX      DisplayString (SIZE (0..255))
    MAX-ACCESS  read-only
    STATUS      deprecated
    DESCRIPTION
            "the interface max rx power."
    ::= { slot13ModuleIfEntry 35 }  

slot13ModuleifTxPowerMin OBJECT-TYPE
    SYNTAX      DisplayString (SIZE (0..255))
    MAX-ACCESS  read-only
    STATUS      deprecated
    DESCRIPTION
            "the interface min tx power."
    ::= { slot13ModuleIfEntry 36 }  

slot13ModuleifTxPowerMax OBJECT-TYPE
    SYNTAX      DisplayString (SIZE (0..255))
    MAX-ACCESS  read-only
    STATUS      deprecated
    DESCRIPTION
            "the interface max tx power."
    ::= { slot13ModuleIfEntry 37 }  

slot13ModuleifRxHisPeak OBJECT-TYPE
    SYNTAX      Counter64
    MAX-ACCESS  read-only
    STATUS      current
    DESCRIPTION
            "The max speed of rx rate on the interface(kbps)"
    ::= { slot13ModuleIfEntry 38 }

slot13ModuleifTxHisPeak OBJECT-TYPE
    SYNTAX      Counter64
    MAX-ACCESS  read-only
    STATUS      current
    DESCRIPTION
            "The max speed of tx rate on the interface(kbps)"
    ::= { slot13ModuleIfEntry 39 }

slot13ModuleifMode OBJECT-TYPE
    SYNTAX      DisplayString (SIZE (0..255))
    MAX-ACCESS  read-only
    STATUS      deprecated
    DESCRIPTION
            "the interface if mode."
    ::= { slot13ModuleIfEntry 40 }  

-- slot 14 --

-- slot14Table --

slot14Table OBJECT-TYPE
    SYNTAX      SEQUENCE OF Slot14Entry
    MAX-ACCESS  not-accessible
    STATUS      current
    DESCRIPTION
            "A list of all slot14Type's utilization."
    ::= { slot14 1 }  

slot14Entry OBJECT-TYPE
    SYNTAX      Slot14Entry
    MAX-ACCESS  not-accessible
    STATUS      current
    DESCRIPTION
            "An entry contains a slot14's utilization."
    INDEX   { slot14Index }
    ::= { slot14Table 1 }

Slot14Entry ::=
    SEQUENCE {     
		slot14Index                       Integer32,
		slot14Type                        DisplayString,
		slot14Status                      DisplayString,
        slot14SerialNumber                DisplayString,		
        slot14Temperature                 DisplayString
    }  

slot14Index OBJECT-TYPE
    SYNTAX      Integer32 (1..2147483647)
    MAX-ACCESS  not-accessible
    STATUS      current
    DESCRIPTION
            "A unique value, greater than zero, for each chassis`s slot14."
    ::= { slot14Entry 1 }

slot14Type OBJECT-TYPE
    SYNTAX      DisplayString (SIZE (0..255))
    MAX-ACCESS  read-only
    STATUS      current
    DESCRIPTION
            "the slot14Type of each chassis."
    ::= { slot14Entry 2 }

slot14Status OBJECT-TYPE
    SYNTAX      DisplayString (SIZE (0..255))
    MAX-ACCESS  read-only
    STATUS      current
    DESCRIPTION
            "A string to describe the board status." 
    ::= { slot14Entry 3 }   

slot14SerialNumber OBJECT-TYPE
    SYNTAX      DisplayString (SIZE (0..255))
    MAX-ACCESS  read-only
    STATUS      current
    DESCRIPTION
            "A string to describe the board serial number." 
    ::= { slot14Entry 4 }   

slot14Temperature OBJECT-TYPE
    SYNTAX      DisplayString (SIZE (0..255))
    MAX-ACCESS  read-only
    STATUS      current
    DESCRIPTION
            "A string to describe the board temperature." 
    ::= { slot14Entry 5 }   


slot14Module OBJECT IDENTIFIER ::= { slot14 2 }

-- slot14ModuleTable --
slot14ModuleTable OBJECT-TYPE
    SYNTAX      SEQUENCE OF Slot14ModuleEntry
    MAX-ACCESS  not-accessible
    STATUS      current
    DESCRIPTION
            "A list of all slot14Module's utilization."
    ::= { slot14Module 1 }  

slot14ModuleEntry OBJECT-TYPE
    SYNTAX      Slot14ModuleEntry
    MAX-ACCESS  not-accessible
    STATUS      current
    DESCRIPTION
            "An entry contains a slot14Module's utilization."
    INDEX   { slot14ModuleIndex }
    ::= { slot14ModuleTable 1 }

Slot14ModuleEntry ::=
    SEQUENCE {     
		slot14ModuleIndex                       Integer32,
		slot14ModuleId                           DisplayString,  
		slot14ModuleIfNumber                     Integer32		
    } 

slot14ModuleIndex OBJECT-TYPE
    SYNTAX      Integer32 (1..2147483647)
    MAX-ACCESS  not-accessible
    STATUS      current
    DESCRIPTION
            "A unique value, greater than zero, for each chassis`s slot14."
    ::= { slot14ModuleEntry 1 }

slot14ModuleId OBJECT-TYPE
    SYNTAX      DisplayString (SIZE (0..32))
    MAX-ACCESS  read-only
    STATUS      current
    DESCRIPTION
            "the value of module`s id"
    ::= { slot14ModuleEntry 2 }
  
slot14ModuleIfNumber OBJECT-TYPE
    SYNTAX      Integer32(0..2147483647)
    MAX-ACCESS  read-only
    STATUS      current
    DESCRIPTION
            "The number of network interfaces (regardless of their
            current state) present on this system." 
    ::= { slot14ModuleEntry 3 } 
    
slot14ModuleIfTable OBJECT-TYPE
    SYNTAX      SEQUENCE OF Slot14ModuleIfEntry
    MAX-ACCESS  not-accessible
    STATUS      current
    DESCRIPTION
            "A list of interface entries.  The number of entries is
            given by the value of ifNumber."
    ::= { slot14Module 2 } 
    
slot14ModuleIfEntry OBJECT-TYPE
    SYNTAX      Slot14ModuleIfEntry
    MAX-ACCESS  not-accessible
    STATUS      current
    DESCRIPTION
            "An entry containing management information applicable to a
            particular interface."
    INDEX   { slot14ModuleifIndex }
    ::= { slot14ModuleIfTable 1 }
    
Slot14ModuleIfEntry ::=
    SEQUENCE {
        slot14ModuleifIndex                 InterfaceIndex,  
        slot14ModuleIfId                    DisplayString,  
        slot14ModuleifDescr                 DisplayString,           
        slot14ModuleifType                  IANAifType,   		
        slot14ModuleifMtu                   Integer32,                
        slot14ModuleifSpeed                 Counter64,               
        slot14ModuleifPhysAddress           PhysAddress,              
        slot14ModuleifAdminStatus           INTEGER,                  
        slot14ModuleifOperStatus            INTEGER,                  
        slot14ModuleifLastChange            TimeTicks,                
        slot14ModuleifInOctets              Counter64,                
        slot14ModuleifInUcastPkts           Counter64,                
        slot14ModuleifInNUcastPkts          Counter64,  
        slot14ModuleifInDiscards            Counter64,
        slot14ModuleifInErrors              Counter64,
        slot14ModuleifInFcsErrorPkts        Counter64,
        slot14ModuleifInUnknownProtos       Counter64,	-- deprecated
        slot14ModuleifOutOctets             Counter64,
        slot14ModuleifOutUcastPkts          Counter64,
        slot14ModuleifOutNUcastPkts         Counter64,  -- deprecated
        slot14ModuleifOutDiscards           Counter64,
        slot14ModuleifOutErrors             Counter64,
        slot14ModuleifOutFcsErrorPkts       Counter64,
        slot14ModuleifOutQLen               Gauge32,    -- deprecated  
        slot14ModuleifOutOctetsRate         Counter64,
        slot14ModuleifInOctetsRate          Counter64,
        slot14ModuleifOutPktsRate           Counter64,
        slot14ModuleifInPktsRate            Counter64,
        slot14ModuleifRxPower               DisplayString,
        slot14ModuleifTxPower               DisplayString,
        slot14ModuleifSpecific              OBJECT IDENTIFIER,
        slot14ModuleifTxMirrorList          DisplayString,
        slot14ModuleifRxMirrorList          DisplayString,
        slot14ModuleifRxPowerMin               DisplayString,
        slot14ModuleifRxPowerMax               DisplayString,
        slot14ModuleifTxPowerMin               DisplayString,
        slot14ModuleifTxPowerMax               DisplayString,
        slot14ModuleifRxHisPeak            Counter64,
        slot14ModuleifTxHisPeak            Counter64,
        slot14ModuleifMode                 DisplayString   		
    }         

slot14ModuleifIndex OBJECT-TYPE
    SYNTAX      InterfaceIndex
    MAX-ACCESS  read-only
    STATUS      current
    DESCRIPTION
            "A unique value, greater than zero, for each interface.  It
            is recommended that values are assigned contiguously
            starting from 1.  The value for each interface sub-layer
            must remain constant at least from one re-initialization of
            the entity's network management system to the next re-
            initialization."
    ::= { slot14ModuleIfEntry 1 }
    
slot14ModuleIfId OBJECT-TYPE
    SYNTAX      DisplayString (SIZE (0..32))
    MAX-ACCESS  read-only
    STATUS      current
    DESCRIPTION
            "the value of module`s id"
    ::= { slot14ModuleIfEntry 2 }
    
slot14ModuleifDescr OBJECT-TYPE
    SYNTAX      DisplayString (SIZE (0..255))
    MAX-ACCESS  read-only
    STATUS      current
    DESCRIPTION
            "A textual string containing information about the
            interface.  This string should include the name of the
            manufacturer, the product name and the version of the
            interface hardware/software."
    ::= { slot14ModuleIfEntry 3 }
    
slot14ModuleifType OBJECT-TYPE
    SYNTAX      IANAifType
    MAX-ACCESS  read-only
    STATUS      current
    DESCRIPTION
            "The type of interface.  Additional values for ifType are
            assigned by the Internet Assigned Numbers Authority (IANA),
            through updating the syntax of the IANAifType textual
            convention."
    ::= { slot14ModuleIfEntry 4 }

slot14ModuleifMtu OBJECT-TYPE
    SYNTAX      Integer32(1..2147483647)
    MAX-ACCESS  read-only
    STATUS      current
    DESCRIPTION
            "The size of the largest packet which can be sent/received
            on the interface, specified in octets.  For interfaces that
            are used for transmitting network datagrams, this is the
            size of the largest network datagram that can be sent on the
            interface."
    ::= { slot14ModuleIfEntry 5 }

slot14ModuleifSpeed OBJECT-TYPE
    SYNTAX      Counter64
    MAX-ACCESS  read-only
    STATUS      current
    DESCRIPTION
            "An estimate of the interface's current bandwidth in bits
            per second.  For interfaces which do not vary in bandwidth
            or for those where no accurate estimation can be made, this
            object should contain the nominal bandwidth. For a sub-layer
            which has no concept of bandwidth, this object should be zero."
    ::= { slot14ModuleIfEntry 6 }

slot14ModuleifPhysAddress OBJECT-TYPE
    SYNTAX      PhysAddress
    MAX-ACCESS  read-only
    STATUS      current
    DESCRIPTION
            "The interface's address at its protocol sub-layer.  For
            example, for an 802.x interface, this object normally
            contains a MAC address.  The interface's media-specific MIB
            must define the bit and byte ordering and the format of the
            value of this object.  For interfaces which do not have such
            an address (e.g., a serial line), this object should contain
            an octet string of zero length."
    ::= { slot14ModuleIfEntry 7 }
    
slot14ModuleifAdminStatus OBJECT-TYPE
    SYNTAX  INTEGER {
                up(1),       -- ready to pass packets
                down(2),
                testing(3)   -- in some test mode
            }
    MAX-ACCESS  read-write
    STATUS      current
    DESCRIPTION
            "The desired state of the interface.  The testing(3) state
            indicates that no operational packets can be passed.  When a
            managed system initializes, all interfaces start with
            ifAdminStatus in the down(2) state.  As a result of either
            explicit management action or per configuration information
            retained by the managed system, ifAdminStatus is then
            changed to either the up(1) or testing(3) states (or remains
            in the down(2) state)."
    ::= { slot14ModuleIfEntry 8 }

slot14ModuleifOperStatus OBJECT-TYPE
    SYNTAX  INTEGER {
                up(1),        -- ready to pass packets
                down(2),
                testing(3),   -- in some test mode
                unknown(4),   -- status can not be determined
                              -- for some reason.
                dormant(5),
                notPresent(6),    -- some component is missing
                lowerLayerDown(7) -- down due to state of
                                  -- lower-layer interface(s)
            }
    MAX-ACCESS  read-only
    STATUS      current
    DESCRIPTION
            "The current operational state of the interface.  The
            testing(3) state indicates that no operational packets can
            be passed.  If ifAdminStatus is down(2) then ifOperStatus
            should be down(2).  If ifAdminStatus is changed to up(1)
            then ifOperStatus should change to up(1) if the interface is
            ready to transmit and receive network traffic; it should
            change to dormant(5) if the interface is waiting for
            external actions (such as a serial line waiting for an
            incoming connection); it should remain in the down(2) state
            if and only if there is a fault that prevents it from going
            to the up(1) state; it should remain in the notPresent(6)
            state if the interface has missing (typically, hardware)
            components."
    ::= { slot14ModuleIfEntry 9 }

slot14ModuleifLastChange OBJECT-TYPE
    SYNTAX      TimeTicks
    MAX-ACCESS  read-only
    STATUS      current
    DESCRIPTION
            "The value of sysUpTime at the time the interface entered
            its current operational state.  If the current state was
            entered prior to the last re-initialization of the local
            network management subsystem, then this object contains a
            zero value."
    ::= { slot14ModuleIfEntry 10 }

slot14ModuleifInOctets OBJECT-TYPE
    SYNTAX      Counter64
    MAX-ACCESS  read-only
    STATUS      current
    DESCRIPTION
            "The total number of octets received on the interface,
            including framing characters.

            Discontinuities in the value of this counter can occur at
            re-initialization of the management system, and at other
            times as indicated by the value of
            ifCounterDiscontinuityTime."
    ::= { slot14ModuleIfEntry 11 }

slot14ModuleifInUcastPkts OBJECT-TYPE
    SYNTAX      Counter64
    MAX-ACCESS  read-only
    STATUS      current
    DESCRIPTION
            "The number of packets, delivered by this sub-layer to a
            higher (sub-)layer, which were not addressed to a multicast
            or broadcast address at this sub-layer.

            Discontinuities in the value of this counter can occur at
            re-initialization of the management system, and at other
            times as indicated by the value of
            ifCounterDiscontinuityTime."
    ::= { slot14ModuleIfEntry 12 }

slot14ModuleifInNUcastPkts OBJECT-TYPE
    SYNTAX  Counter64
    MAX-ACCESS  read-only
    STATUS      current
    DESCRIPTION
            "The number of packets, delivered by this sub-layer to a
            higher (sub-)layer, which were addressed to a multicast or
            broadcast address at this sub-layer.

            Discontinuities in the value of this counter can occur at
            re-initialization of the management system, and at other
            times as indicated by the value of
            ifCounterDiscontinuityTime.

            This object is deprecated in favour of ifInMulticastPkts and
            ifInBroadcastPkts."
    ::= { slot14ModuleIfEntry 13 }

slot14ModuleifInDiscards OBJECT-TYPE
    SYNTAX      Counter64
    MAX-ACCESS  read-only
    STATUS      current
    DESCRIPTION
            "The number of inbound packets which were chosen to be
            discarded even though no errors had been detected to prevent

            their being deliverable to a higher-layer protocol.  One
            possible reason for discarding such a packet could be to
            free up buffer space.

            Discontinuities in the value of this counter can occur at
            re-initialization of the management system, and at other
            times as indicated by the value of
            ifCounterDiscontinuityTime."
    ::= { slot14ModuleIfEntry 14 }

slot14ModuleifInErrors OBJECT-TYPE
    SYNTAX      Counter64
    MAX-ACCESS  read-only
    STATUS      current
    DESCRIPTION
            "For packet-oriented interfaces, the number of inbound
            packets that contained errors preventing them from being
            deliverable to a higher-layer protocol.  For character-
            oriented or fixed-length interfaces, the number of inbound
            transmission units that contained errors preventing them
            from being deliverable to a higher-layer protocol.

            Discontinuities in the value of this counter can occur at
            re-initialization of the management system, and at other
            times as indicated by the value of
            ifCounterDiscontinuityTime."
    ::= { slot14ModuleIfEntry 15 }

slot14ModuleifInFcsErrorPkts OBJECT-TYPE
    SYNTAX      Counter64
    MAX-ACCESS  read-only
    STATUS      current
    DESCRIPTION
            "FCS error pakets."
    ::= { slot14ModuleIfEntry 16 }

slot14ModuleifInUnknownProtos OBJECT-TYPE
    SYNTAX      Counter64
    MAX-ACCESS  read-only
    STATUS      current
    DESCRIPTION
            "For packet-oriented interfaces, the number of packets
            received via the interface which were discarded because of
            an unknown or unsupported protocol.  For character-oriented
            or fixed-length interfaces that support protocol
            multiplexing the number of transmission units received via
            the interface which were discarded because of an unknown or
            unsupported protocol.  For any interface that does not
            support protocol multiplexing, this counter will always be
            0.

            Discontinuities in the value of this counter can occur at
            re-initialization of the management system, and at other
            times as indicated by the value of
            ifCounterDiscontinuityTime."
    ::= { slot14ModuleIfEntry 17 }

slot14ModuleifOutOctets OBJECT-TYPE
    SYNTAX      Counter64
    MAX-ACCESS  read-only
    STATUS      current
    DESCRIPTION
            "The total number of octets transmitted out of the
            interface, including framing characters.

            Discontinuities in the value of this counter can occur at
            re-initialization of the management system, and at other
            times as indicated by the value of
            ifCounterDiscontinuityTime."
    ::= { slot14ModuleIfEntry 18 }

slot14ModuleifOutUcastPkts OBJECT-TYPE
    SYNTAX      Counter64
    MAX-ACCESS  read-only
    STATUS      current
    DESCRIPTION
            "The total number of packets that higher-level protocols
            requested be transmitted, and which were not addressed to a
            multicast or broadcast address at this sub-layer, including
            those that were discarded or not sent.

            Discontinuities in the value of this counter can occur at
            re-initialization of the management system, and at other
            times as indicated by the value of
            ifCounterDiscontinuityTime."
    ::= { slot14ModuleIfEntry 19 }

slot14ModuleifOutNUcastPkts OBJECT-TYPE
    SYNTAX      Counter64
    MAX-ACCESS  read-only
    STATUS      deprecated
    DESCRIPTION
            "The total number of packets that higher-level protocols
            requested be transmitted, and which were addressed to a
            multicast or broadcast address at this sub-layer, including
            those that were discarded or not sent.

            Discontinuities in the value of this counter can occur at
            re-initialization of the management system, and at other
            times as indicated by the value of
            ifCounterDiscontinuityTime.

            This object is deprecated in favour of ifOutMulticastPkts
            and ifOutBroadcastPkts."
    ::= { slot14ModuleIfEntry 20 }

slot14ModuleifOutDiscards OBJECT-TYPE
    SYNTAX      Counter64
    MAX-ACCESS  read-only
    STATUS      current
    DESCRIPTION
            "The number of outbound packets which were chosen to be
            discarded even though no errors had been detected to prevent
            their being transmitted.  One possible reason for discarding
            such a packet could be to free up buffer space.

            Discontinuities in the value of this counter can occur at
            re-initialization of the management system, and at other
            times as indicated by the value of
            ifCounterDiscontinuityTime."
    ::= { slot14ModuleIfEntry 21 }

slot14ModuleifOutErrors OBJECT-TYPE
    SYNTAX      Counter64
    MAX-ACCESS  read-only
    STATUS      current
    DESCRIPTION
            "For packet-oriented interfaces, the number of outbound
            packets that could not be transmitted because of errors.
            For character-oriented or fixed-length interfaces, the
            number of outbound transmission units that could not be
            transmitted because of errors.

            Discontinuities in the value of this counter can occur at
            re-initialization of the management system, and at other
            times as indicated by the value of
            ifCounterDiscontinuityTime."
    ::= { slot14ModuleIfEntry 22 }

slot14ModuleifOutFcsErrorPkts OBJECT-TYPE
    SYNTAX      Counter64
    MAX-ACCESS  read-only
    STATUS      current
    DESCRIPTION
            "FCS error pakets."
    ::= { slot14ModuleIfEntry 23 }

slot14ModuleifOutQLen OBJECT-TYPE
    SYNTAX      Gauge32
    MAX-ACCESS  read-only
    STATUS      deprecated
    DESCRIPTION
            "The length of the output packet queue (in packets)."
    ::= { slot14ModuleIfEntry 24 }

slot14ModuleifOutOctetsRate OBJECT-TYPE
    SYNTAX      Counter64
    MAX-ACCESS  read-only
    STATUS      current
    DESCRIPTION
            "The speed of octets trans on the interface(kbps)"
    ::= { slot14ModuleIfEntry 25 }

slot14ModuleifInOctetsRate OBJECT-TYPE
    SYNTAX      Counter64
    MAX-ACCESS  read-only
    STATUS      current
    DESCRIPTION
            "The speed of octets received on the interface(kbps)"
    ::= { slot14ModuleIfEntry 26 }

slot14ModuleifOutPktsRate OBJECT-TYPE
    SYNTAX      Counter64
    MAX-ACCESS  read-only
    STATUS      current
    DESCRIPTION
            "The speed of packets trans on the interface(pps)"
    ::= { slot14ModuleIfEntry 27 }

slot14ModuleifInPktsRate OBJECT-TYPE
    SYNTAX      Counter64
    MAX-ACCESS  read-only
    STATUS      current
    DESCRIPTION
            "The speed of octets received on the interface(kbps)"
    ::= { slot14ModuleIfEntry 28 }

slot14ModuleifRxPower OBJECT-TYPE
    SYNTAX      DisplayString (SIZE (0..255))
    MAX-ACCESS  read-only
    STATUS      current
    DESCRIPTION
            "the value of interface's received power, in dbm format."
    ::= { slot14ModuleIfEntry 29 }

slot14ModuleifTxPower OBJECT-TYPE
    SYNTAX      DisplayString (SIZE (0..255))
    MAX-ACCESS  read-only
    STATUS      current
    DESCRIPTION
            "the value of interface's send power, in dbm format."
    ::= { slot14ModuleIfEntry 30 }

slot14ModuleifSpecific OBJECT-TYPE
    SYNTAX      OBJECT IDENTIFIER
    MAX-ACCESS  read-only
    STATUS      deprecated
    DESCRIPTION
            "A reference to MIB definitions specific to the particular
            media being used to realize the interface.  It is

            recommended that this value point to an instance of a MIB
            object in the media-specific MIB, i.e., that this object
            have the semantics associated with the InstancePointer
            textual convention defined in RFC 2579.  In fact, it is
            recommended that the media-specific MIB specify what value
            ifSpecific should/can take for values of ifType.  If no MIB
            definitions specific to the particular media are available,
            the value should be set to the OBJECT IDENTIFIER { 0 0 }."
    ::= { slot14ModuleIfEntry 31 }  
  
slot14ModuleifTxMirrorList OBJECT-TYPE
    SYNTAX      DisplayString (SIZE (0..255))
    MAX-ACCESS  read-only
    STATUS      deprecated
    DESCRIPTION
            "the interface tx mirror list."
    ::= { slot14ModuleIfEntry 32 }  
 
slot14ModuleifRxMirrorList OBJECT-TYPE
    SYNTAX      DisplayString (SIZE (0..255))
    MAX-ACCESS  read-only
    STATUS      deprecated
    DESCRIPTION
            "the interface rx mirror list."
    ::= { slot14ModuleIfEntry 33 }  

slot14ModuleifRxPowerMin OBJECT-TYPE
    SYNTAX      DisplayString (SIZE (0..255))
    MAX-ACCESS  read-only
    STATUS      deprecated
    DESCRIPTION
            "the interface min rx power."
    ::= { slot14ModuleIfEntry 34 }  

slot14ModuleifRxPowerMax OBJECT-TYPE
    SYNTAX      DisplayString (SIZE (0..255))
    MAX-ACCESS  read-only
    STATUS      deprecated
    DESCRIPTION
            "the interface max rx power."
    ::= { slot14ModuleIfEntry 35 }  

slot14ModuleifTxPowerMin OBJECT-TYPE
    SYNTAX      DisplayString (SIZE (0..255))
    MAX-ACCESS  read-only
    STATUS      deprecated
    DESCRIPTION
            "the interface min tx power."
    ::= { slot14ModuleIfEntry 36 }  

slot14ModuleifTxPowerMax OBJECT-TYPE
    SYNTAX      DisplayString (SIZE (0..255))
    MAX-ACCESS  read-only
    STATUS      deprecated
    DESCRIPTION
            "the interface max tx power."
    ::= { slot14ModuleIfEntry 37 }  

slot14ModuleifRxHisPeak OBJECT-TYPE
    SYNTAX      Counter64
    MAX-ACCESS  read-only
    STATUS      current
    DESCRIPTION
            "The max speed of rx rate on the interface(kbps)"
    ::= { slot14ModuleIfEntry 38 }

slot14ModuleifTxHisPeak OBJECT-TYPE
    SYNTAX      Counter64
    MAX-ACCESS  read-only
    STATUS      current
    DESCRIPTION
            "The max speed of tx rate on the interface(kbps)"
    ::= { slot14ModuleIfEntry 39 }

slot14ModuleifMode OBJECT-TYPE
    SYNTAX      DisplayString (SIZE (0..255))
    MAX-ACCESS  read-only
    STATUS      deprecated
    DESCRIPTION
            "the interface if mode."
    ::= { slot14ModuleIfEntry 40 }  


-- slot 15 --

-- slot15Table --

slot15Table OBJECT-TYPE
    SYNTAX      SEQUENCE OF Slot15Entry
    MAX-ACCESS  not-accessible
    STATUS      current
    DESCRIPTION
            "A list of all slot15Type's utilization."
    ::= { slot15 1 }  

slot15Entry OBJECT-TYPE
    SYNTAX      Slot15Entry
    MAX-ACCESS  not-accessible
    STATUS      current
    DESCRIPTION
            "An entry contains a slot15's utilization."
    INDEX   { slot15Index }
    ::= { slot15Table 1 }

Slot15Entry ::=
    SEQUENCE {     
		slot15Index                       Integer32,
		slot15Type                        DisplayString,
		slot15Status                      DisplayString,
        slot15SerialNumber                DisplayString,		
        slot15Temperature                 DisplayString
    }  

slot15Index OBJECT-TYPE
    SYNTAX      Integer32 (1..2147483647)
    MAX-ACCESS  not-accessible
    STATUS      current
    DESCRIPTION
            "A unique value, greater than zero, for each chassis`s slot15."
    ::= { slot15Entry 1 }

slot15Type OBJECT-TYPE
    SYNTAX      DisplayString (SIZE (0..255))
    MAX-ACCESS  read-only
    STATUS      current
    DESCRIPTION
            "the slot15Type of each chassis."
    ::= { slot15Entry 2 }

slot15Status OBJECT-TYPE
    SYNTAX      DisplayString (SIZE (0..255))
    MAX-ACCESS  read-only
    STATUS      current
    DESCRIPTION
            "A string to describe the board status." 
    ::= { slot15Entry 3 }   

slot15SerialNumber OBJECT-TYPE
    SYNTAX      DisplayString (SIZE (0..255))
    MAX-ACCESS  read-only
    STATUS      current
    DESCRIPTION
            "A string to describe the board serial number." 
    ::= { slot15Entry 4 }   

slot15Temperature OBJECT-TYPE
    SYNTAX      DisplayString (SIZE (0..255))
    MAX-ACCESS  read-only
    STATUS      current
    DESCRIPTION
            "A string to describe the board temperature." 
    ::= { slot15Entry 5 }   


slot15Module OBJECT IDENTIFIER ::= { slot15 2 }

-- slot15ModuleTable --
slot15ModuleTable OBJECT-TYPE
    SYNTAX      SEQUENCE OF Slot15ModuleEntry
    MAX-ACCESS  not-accessible
    STATUS      current
    DESCRIPTION
            "A list of all slot15Module's utilization."
    ::= { slot15Module 1 }  

slot15ModuleEntry OBJECT-TYPE
    SYNTAX      Slot15ModuleEntry
    MAX-ACCESS  not-accessible
    STATUS      current
    DESCRIPTION
            "An entry contains a slot15Module's utilization."
    INDEX   { slot15ModuleIndex }
    ::= { slot15ModuleTable 1 }

Slot15ModuleEntry ::=
    SEQUENCE {     
		slot15ModuleIndex                       Integer32,
		slot15ModuleId                           DisplayString,  
		slot15ModuleIfNumber                     Integer32		
    } 

slot15ModuleIndex OBJECT-TYPE
    SYNTAX      Integer32 (1..2147483647)
    MAX-ACCESS  not-accessible
    STATUS      current
    DESCRIPTION
            "A unique value, greater than zero, for each chassis`s slot15."
    ::= { slot15ModuleEntry 1 }

slot15ModuleId OBJECT-TYPE
    SYNTAX      DisplayString (SIZE (0..32))
    MAX-ACCESS  read-only
    STATUS      current
    DESCRIPTION
            "the value of module`s id"
    ::= { slot15ModuleEntry 2 }
  
slot15ModuleIfNumber OBJECT-TYPE
    SYNTAX      Integer32(0..2147483647)
    MAX-ACCESS  read-only
    STATUS      current
    DESCRIPTION
            "The number of network interfaces (regardless of their
            current state) present on this system." 
    ::= { slot15ModuleEntry 3 } 
    
slot15ModuleIfTable OBJECT-TYPE
    SYNTAX      SEQUENCE OF Slot15ModuleIfEntry
    MAX-ACCESS  not-accessible
    STATUS      current
    DESCRIPTION
            "A list of interface entries.  The number of entries is
            given by the value of ifNumber."
    ::= { slot15Module 2 } 
    
slot15ModuleIfEntry OBJECT-TYPE
    SYNTAX      Slot15ModuleIfEntry
    MAX-ACCESS  not-accessible
    STATUS      current
    DESCRIPTION
            "An entry containing management information applicable to a
            particular interface."
    INDEX   { slot15ModuleifIndex }
    ::= { slot15ModuleIfTable 1 }
    
Slot15ModuleIfEntry ::=
    SEQUENCE {
        slot15ModuleifIndex                 InterfaceIndex,  
        slot15ModuleIfId                    DisplayString,  
        slot15ModuleifDescr                 DisplayString,           
        slot15ModuleifType                  IANAifType,   		
        slot15ModuleifMtu                   Integer32,                
        slot15ModuleifSpeed                 Counter64,               
        slot15ModuleifPhysAddress           PhysAddress,              
        slot15ModuleifAdminStatus           INTEGER,                  
        slot15ModuleifOperStatus            INTEGER,                  
        slot15ModuleifLastChange            TimeTicks,                
        slot15ModuleifInOctets              Counter64,                
        slot15ModuleifInUcastPkts           Counter64,                
        slot15ModuleifInNUcastPkts          Counter64,  
        slot15ModuleifInDiscards            Counter64,
        slot15ModuleifInErrors              Counter64,
        slot15ModuleifInFcsErrorPkts        Counter64,
        slot15ModuleifInUnknownProtos       Counter64,	-- deprecated
        slot15ModuleifOutOctets             Counter64,
        slot15ModuleifOutUcastPkts          Counter64,
        slot15ModuleifOutNUcastPkts         Counter64,  -- deprecated
        slot15ModuleifOutDiscards           Counter64,
        slot15ModuleifOutErrors             Counter64,
        slot15ModuleifOutFcsErrorPkts       Counter64,
        slot15ModuleifOutQLen               Gauge32,    -- deprecated  
        slot15ModuleifOutOctetsRate         Counter64,
        slot15ModuleifInOctetsRate          Counter64,
        slot15ModuleifOutPktsRate           Counter64,
        slot15ModuleifInPktsRate            Counter64,
        slot15ModuleifRxPower               DisplayString,
        slot15ModuleifTxPower               DisplayString,
        slot15ModuleifSpecific              OBJECT IDENTIFIER,
        slot15ModuleifTxMirrorList          DisplayString,
        slot15ModuleifRxMirrorList          DisplayString,
        slot15ModuleifRxPowerMin               DisplayString,
        slot15ModuleifRxPowerMax               DisplayString,
        slot15ModuleifTxPowerMin               DisplayString,
        slot15ModuleifTxPowerMax               DisplayString,
        slot15ModuleifRxHisPeak            Counter64,
        slot15ModuleifTxHisPeak            Counter64,
        slot15ModuleifMode                 DisplayString   		
    }         

slot15ModuleifIndex OBJECT-TYPE
    SYNTAX      InterfaceIndex
    MAX-ACCESS  read-only
    STATUS      current
    DESCRIPTION
            "A unique value, greater than zero, for each interface.  It
            is recommended that values are assigned contiguously
            starting from 1.  The value for each interface sub-layer
            must remain constant at least from one re-initialization of
            the entity's network management system to the next re-
            initialization."
    ::= { slot15ModuleIfEntry 1 }
    
slot15ModuleIfId OBJECT-TYPE
    SYNTAX      DisplayString (SIZE (0..32))
    MAX-ACCESS  read-only
    STATUS      current
    DESCRIPTION
            "the value of module`s id"
    ::= { slot15ModuleIfEntry 2 }
    
slot15ModuleifDescr OBJECT-TYPE
    SYNTAX      DisplayString (SIZE (0..255))
    MAX-ACCESS  read-only
    STATUS      current
    DESCRIPTION
            "A textual string containing information about the
            interface.  This string should include the name of the
            manufacturer, the product name and the version of the
            interface hardware/software."
    ::= { slot15ModuleIfEntry 3 }
    
slot15ModuleifType OBJECT-TYPE
    SYNTAX      IANAifType
    MAX-ACCESS  read-only
    STATUS      current
    DESCRIPTION
            "The type of interface.  Additional values for ifType are
            assigned by the Internet Assigned Numbers Authority (IANA),
            through updating the syntax of the IANAifType textual
            convention."
    ::= { slot15ModuleIfEntry 4 }

slot15ModuleifMtu OBJECT-TYPE
    SYNTAX      Integer32(1..2147483647)
    MAX-ACCESS  read-only
    STATUS      current
    DESCRIPTION
            "The size of the largest packet which can be sent/received
            on the interface, specified in octets.  For interfaces that
            are used for transmitting network datagrams, this is the
            size of the largest network datagram that can be sent on the
            interface."
    ::= { slot15ModuleIfEntry 5 }

slot15ModuleifSpeed OBJECT-TYPE
    SYNTAX      Counter64
    MAX-ACCESS  read-only
    STATUS      current
    DESCRIPTION
            "An estimate of the interface's current bandwidth in bits
            per second.  For interfaces which do not vary in bandwidth
            or for those where no accurate estimation can be made, this
            object should contain the nominal bandwidth. For a sub-layer
            which has no concept of bandwidth, this object should be zero."
    ::= { slot15ModuleIfEntry 6 }

slot15ModuleifPhysAddress OBJECT-TYPE
    SYNTAX      PhysAddress
    MAX-ACCESS  read-only
    STATUS      current
    DESCRIPTION
            "The interface's address at its protocol sub-layer.  For
            example, for an 802.x interface, this object normally
            contains a MAC address.  The interface's media-specific MIB
            must define the bit and byte ordering and the format of the
            value of this object.  For interfaces which do not have such
            an address (e.g., a serial line), this object should contain
            an octet string of zero length."
    ::= { slot15ModuleIfEntry 7 }
    
slot15ModuleifAdminStatus OBJECT-TYPE
    SYNTAX  INTEGER {
                up(1),       -- ready to pass packets
                down(2),
                testing(3)   -- in some test mode
            }
    MAX-ACCESS  read-write
    STATUS      current
    DESCRIPTION
            "The desired state of the interface.  The testing(3) state
            indicates that no operational packets can be passed.  When a
            managed system initializes, all interfaces start with
            ifAdminStatus in the down(2) state.  As a result of either
            explicit management action or per configuration information
            retained by the managed system, ifAdminStatus is then
            changed to either the up(1) or testing(3) states (or remains
            in the down(2) state)."
    ::= { slot15ModuleIfEntry 8 }

slot15ModuleifOperStatus OBJECT-TYPE
    SYNTAX  INTEGER {
                up(1),        -- ready to pass packets
                down(2),
                testing(3),   -- in some test mode
                unknown(4),   -- status can not be determined
                              -- for some reason.
                dormant(5),
                notPresent(6),    -- some component is missing
                lowerLayerDown(7) -- down due to state of
                                  -- lower-layer interface(s)
            }
    MAX-ACCESS  read-only
    STATUS      current
    DESCRIPTION
            "The current operational state of the interface.  The
            testing(3) state indicates that no operational packets can
            be passed.  If ifAdminStatus is down(2) then ifOperStatus
            should be down(2).  If ifAdminStatus is changed to up(1)
            then ifOperStatus should change to up(1) if the interface is
            ready to transmit and receive network traffic; it should
            change to dormant(5) if the interface is waiting for
            external actions (such as a serial line waiting for an
            incoming connection); it should remain in the down(2) state
            if and only if there is a fault that prevents it from going
            to the up(1) state; it should remain in the notPresent(6)
            state if the interface has missing (typically, hardware)
            components."
    ::= { slot15ModuleIfEntry 9 }

slot15ModuleifLastChange OBJECT-TYPE
    SYNTAX      TimeTicks
    MAX-ACCESS  read-only
    STATUS      current
    DESCRIPTION
            "The value of sysUpTime at the time the interface entered
            its current operational state.  If the current state was
            entered prior to the last re-initialization of the local
            network management subsystem, then this object contains a
            zero value."
    ::= { slot15ModuleIfEntry 10 }

slot15ModuleifInOctets OBJECT-TYPE
    SYNTAX      Counter64
    MAX-ACCESS  read-only
    STATUS      current
    DESCRIPTION
            "The total number of octets received on the interface,
            including framing characters.

            Discontinuities in the value of this counter can occur at
            re-initialization of the management system, and at other
            times as indicated by the value of
            ifCounterDiscontinuityTime."
    ::= { slot15ModuleIfEntry 11 }

slot15ModuleifInUcastPkts OBJECT-TYPE
    SYNTAX      Counter64
    MAX-ACCESS  read-only
    STATUS      current
    DESCRIPTION
            "The number of packets, delivered by this sub-layer to a
            higher (sub-)layer, which were not addressed to a multicast
            or broadcast address at this sub-layer.

            Discontinuities in the value of this counter can occur at
            re-initialization of the management system, and at other
            times as indicated by the value of
            ifCounterDiscontinuityTime."
    ::= { slot15ModuleIfEntry 12 }

slot15ModuleifInNUcastPkts OBJECT-TYPE
    SYNTAX  Counter64
    MAX-ACCESS  read-only
    STATUS      current
    DESCRIPTION
            "The number of packets, delivered by this sub-layer to a
            higher (sub-)layer, which were addressed to a multicast or
            broadcast address at this sub-layer.

            Discontinuities in the value of this counter can occur at
            re-initialization of the management system, and at other
            times as indicated by the value of
            ifCounterDiscontinuityTime.

            This object is deprecated in favour of ifInMulticastPkts and
            ifInBroadcastPkts."
    ::= { slot15ModuleIfEntry 13 }

slot15ModuleifInDiscards OBJECT-TYPE
    SYNTAX      Counter64
    MAX-ACCESS  read-only
    STATUS      current
    DESCRIPTION
            "The number of inbound packets which were chosen to be
            discarded even though no errors had been detected to prevent

            their being deliverable to a higher-layer protocol.  One
            possible reason for discarding such a packet could be to
            free up buffer space.

            Discontinuities in the value of this counter can occur at
            re-initialization of the management system, and at other
            times as indicated by the value of
            ifCounterDiscontinuityTime."
    ::= { slot15ModuleIfEntry 14 }

slot15ModuleifInErrors OBJECT-TYPE
    SYNTAX      Counter64
    MAX-ACCESS  read-only
    STATUS      current
    DESCRIPTION
            "For packet-oriented interfaces, the number of inbound
            packets that contained errors preventing them from being
            deliverable to a higher-layer protocol.  For character-
            oriented or fixed-length interfaces, the number of inbound
            transmission units that contained errors preventing them
            from being deliverable to a higher-layer protocol.

            Discontinuities in the value of this counter can occur at
            re-initialization of the management system, and at other
            times as indicated by the value of
            ifCounterDiscontinuityTime."
    ::= { slot15ModuleIfEntry 15 }

slot15ModuleifInFcsErrorPkts OBJECT-TYPE
    SYNTAX      Counter64
    MAX-ACCESS  read-only
    STATUS      current
    DESCRIPTION
            "FCS error pakets."
    ::= { slot15ModuleIfEntry 16 }

slot15ModuleifInUnknownProtos OBJECT-TYPE
    SYNTAX      Counter64
    MAX-ACCESS  read-only
    STATUS      current
    DESCRIPTION
            "For packet-oriented interfaces, the number of packets
            received via the interface which were discarded because of
            an unknown or unsupported protocol.  For character-oriented
            or fixed-length interfaces that support protocol
            multiplexing the number of transmission units received via
            the interface which were discarded because of an unknown or
            unsupported protocol.  For any interface that does not
            support protocol multiplexing, this counter will always be
            0.

            Discontinuities in the value of this counter can occur at
            re-initialization of the management system, and at other
            times as indicated by the value of
            ifCounterDiscontinuityTime."
    ::= { slot15ModuleIfEntry 17 }

slot15ModuleifOutOctets OBJECT-TYPE
    SYNTAX      Counter64
    MAX-ACCESS  read-only
    STATUS      current
    DESCRIPTION
            "The total number of octets transmitted out of the
            interface, including framing characters.

            Discontinuities in the value of this counter can occur at
            re-initialization of the management system, and at other
            times as indicated by the value of
            ifCounterDiscontinuityTime."
    ::= { slot15ModuleIfEntry 18 }

slot15ModuleifOutUcastPkts OBJECT-TYPE
    SYNTAX      Counter64
    MAX-ACCESS  read-only
    STATUS      current
    DESCRIPTION
            "The total number of packets that higher-level protocols
            requested be transmitted, and which were not addressed to a
            multicast or broadcast address at this sub-layer, including
            those that were discarded or not sent.

            Discontinuities in the value of this counter can occur at
            re-initialization of the management system, and at other
            times as indicated by the value of
            ifCounterDiscontinuityTime."
    ::= { slot15ModuleIfEntry 19 }

slot15ModuleifOutNUcastPkts OBJECT-TYPE
    SYNTAX      Counter64
    MAX-ACCESS  read-only
    STATUS      deprecated
    DESCRIPTION
            "The total number of packets that higher-level protocols
            requested be transmitted, and which were addressed to a
            multicast or broadcast address at this sub-layer, including
            those that were discarded or not sent.

            Discontinuities in the value of this counter can occur at
            re-initialization of the management system, and at other
            times as indicated by the value of
            ifCounterDiscontinuityTime.

            This object is deprecated in favour of ifOutMulticastPkts
            and ifOutBroadcastPkts."
    ::= { slot15ModuleIfEntry 20 }

slot15ModuleifOutDiscards OBJECT-TYPE
    SYNTAX      Counter64
    MAX-ACCESS  read-only
    STATUS      current
    DESCRIPTION
            "The number of outbound packets which were chosen to be
            discarded even though no errors had been detected to prevent
            their being transmitted.  One possible reason for discarding
            such a packet could be to free up buffer space.

            Discontinuities in the value of this counter can occur at
            re-initialization of the management system, and at other
            times as indicated by the value of
            ifCounterDiscontinuityTime."
    ::= { slot15ModuleIfEntry 21 }

slot15ModuleifOutErrors OBJECT-TYPE
    SYNTAX      Counter64
    MAX-ACCESS  read-only
    STATUS      current
    DESCRIPTION
            "For packet-oriented interfaces, the number of outbound
            packets that could not be transmitted because of errors.
            For character-oriented or fixed-length interfaces, the
            number of outbound transmission units that could not be
            transmitted because of errors.

            Discontinuities in the value of this counter can occur at
            re-initialization of the management system, and at other
            times as indicated by the value of
            ifCounterDiscontinuityTime."
    ::= { slot15ModuleIfEntry 22 }

slot15ModuleifOutFcsErrorPkts OBJECT-TYPE
    SYNTAX      Counter64
    MAX-ACCESS  read-only
    STATUS      current
    DESCRIPTION
            "FCS error pakets."
    ::= { slot15ModuleIfEntry 23 }

slot15ModuleifOutQLen OBJECT-TYPE
    SYNTAX      Gauge32
    MAX-ACCESS  read-only
    STATUS      deprecated
    DESCRIPTION
            "The length of the output packet queue (in packets)."
    ::= { slot15ModuleIfEntry 24 }

slot15ModuleifOutOctetsRate OBJECT-TYPE
    SYNTAX      Counter64
    MAX-ACCESS  read-only
    STATUS      current
    DESCRIPTION
            "The speed of octets trans on the interface(kbps)"
    ::= { slot15ModuleIfEntry 25 }

slot15ModuleifInOctetsRate OBJECT-TYPE
    SYNTAX      Counter64
    MAX-ACCESS  read-only
    STATUS      current
    DESCRIPTION
            "The speed of octets received on the interface(kbps)"
    ::= { slot15ModuleIfEntry 26 }

slot15ModuleifOutPktsRate OBJECT-TYPE
    SYNTAX      Counter64
    MAX-ACCESS  read-only
    STATUS      current
    DESCRIPTION
            "The speed of packets trans on the interface(pps)"
    ::= { slot15ModuleIfEntry 27 }

slot15ModuleifInPktsRate OBJECT-TYPE
    SYNTAX      Counter64
    MAX-ACCESS  read-only
    STATUS      current
    DESCRIPTION
            "The speed of octets received on the interface(kbps)"
    ::= { slot15ModuleIfEntry 28 }

slot15ModuleifRxPower OBJECT-TYPE
    SYNTAX      DisplayString (SIZE (0..255))
    MAX-ACCESS  read-only
    STATUS      current
    DESCRIPTION
            "the value of interface's received power, in dbm format."
    ::= { slot15ModuleIfEntry 29 }

slot15ModuleifTxPower OBJECT-TYPE
    SYNTAX      DisplayString (SIZE (0..255))
    MAX-ACCESS  read-only
    STATUS      current
    DESCRIPTION
            "the value of interface's send power, in dbm format."
    ::= { slot15ModuleIfEntry 30 }

slot15ModuleifSpecific OBJECT-TYPE
    SYNTAX      OBJECT IDENTIFIER
    MAX-ACCESS  read-only
    STATUS      deprecated
    DESCRIPTION
            "A reference to MIB definitions specific to the particular
            media being used to realize the interface.  It is

            recommended that this value point to an instance of a MIB
            object in the media-specific MIB, i.e., that this object
            have the semantics associated with the InstancePointer
            textual convention defined in RFC 2579.  In fact, it is
            recommended that the media-specific MIB specify what value
            ifSpecific should/can take for values of ifType.  If no MIB
            definitions specific to the particular media are available,
            the value should be set to the OBJECT IDENTIFIER { 0 0 }."
    ::= { slot15ModuleIfEntry 31 }  
  
slot15ModuleifTxMirrorList OBJECT-TYPE
    SYNTAX      DisplayString (SIZE (0..255))
    MAX-ACCESS  read-only
    STATUS      deprecated
    DESCRIPTION
            "the interface tx mirror list."
    ::= { slot15ModuleIfEntry 32 }  
 
slot15ModuleifRxMirrorList OBJECT-TYPE
    SYNTAX      DisplayString (SIZE (0..255))
    MAX-ACCESS  read-only
    STATUS      deprecated
    DESCRIPTION
            "the interface rx mirror list."
    ::= { slot15ModuleIfEntry 33 }  

slot15ModuleifRxPowerMin OBJECT-TYPE
    SYNTAX      DisplayString (SIZE (0..255))
    MAX-ACCESS  read-only
    STATUS      deprecated
    DESCRIPTION
            "the interface min rx power."
    ::= { slot15ModuleIfEntry 34 }  

slot15ModuleifRxPowerMax OBJECT-TYPE
    SYNTAX      DisplayString (SIZE (0..255))
    MAX-ACCESS  read-only
    STATUS      deprecated
    DESCRIPTION
            "the interface max rx power."
    ::= { slot15ModuleIfEntry 35 }  

slot15ModuleifTxPowerMin OBJECT-TYPE
    SYNTAX      DisplayString (SIZE (0..255))
    MAX-ACCESS  read-only
    STATUS      deprecated
    DESCRIPTION
            "the interface min tx power."
    ::= { slot15ModuleIfEntry 36 }  

slot15ModuleifTxPowerMax OBJECT-TYPE
    SYNTAX      DisplayString (SIZE (0..255))
    MAX-ACCESS  read-only
    STATUS      deprecated
    DESCRIPTION
            "the interface max tx power."
    ::= { slot15ModuleIfEntry 37 }  

slot15ModuleifRxHisPeak OBJECT-TYPE
    SYNTAX      Counter64
    MAX-ACCESS  read-only
    STATUS      current
    DESCRIPTION
            "The max speed of rx rate on the interface(kbps)"
    ::= { slot15ModuleIfEntry 38 }

slot15ModuleifTxHisPeak OBJECT-TYPE
    SYNTAX      Counter64
    MAX-ACCESS  read-only
    STATUS      current
    DESCRIPTION
            "The max speed of tx rate on the interface(kbps)"
    ::= { slot15ModuleIfEntry 39 }

slot15ModuleifMode OBJECT-TYPE
    SYNTAX      DisplayString (SIZE (0..255))
    MAX-ACCESS  read-only
    STATUS      deprecated
    DESCRIPTION
            "the interface if mode."
    ::= { slot15ModuleIfEntry 40 }  


-- slot 16 --

-- slot16Table --

slot16Table OBJECT-TYPE
    SYNTAX      SEQUENCE OF Slot16Entry
    MAX-ACCESS  not-accessible
    STATUS      current
    DESCRIPTION
            "A list of all slot16Type's utilization."
    ::= { slot16 1 }  

slot16Entry OBJECT-TYPE
    SYNTAX      Slot16Entry
    MAX-ACCESS  not-accessible
    STATUS      current
    DESCRIPTION
            "An entry contains a slot16's utilization."
    INDEX   { slot16Index }
    ::= { slot16Table 1 }

Slot16Entry ::=
    SEQUENCE {     
		slot16Index                       Integer32,
		slot16Type                        DisplayString,
		slot16Status                      DisplayString,
        slot16SerialNumber                DisplayString,		
        slot16Temperature                 DisplayString
    }  

slot16Index OBJECT-TYPE
    SYNTAX      Integer32 (1..2147483647)
    MAX-ACCESS  not-accessible
    STATUS      current
    DESCRIPTION
            "A unique value, greater than zero, for each chassis`s slot16."
    ::= { slot16Entry 1 }

slot16Type OBJECT-TYPE
    SYNTAX      DisplayString (SIZE (0..255))
    MAX-ACCESS  read-only
    STATUS      current
    DESCRIPTION
            "the slot16Type of each chassis."
    ::= { slot16Entry 2 }

slot16Status OBJECT-TYPE
    SYNTAX      DisplayString (SIZE (0..255))
    MAX-ACCESS  read-only
    STATUS      current
    DESCRIPTION
            "A string to describe the board status." 
    ::= { slot16Entry 3 }   

slot16SerialNumber OBJECT-TYPE
    SYNTAX      DisplayString (SIZE (0..255))
    MAX-ACCESS  read-only
    STATUS      current
    DESCRIPTION
            "A string to describe the board serial number." 
    ::= { slot16Entry 4 }   

slot16Temperature OBJECT-TYPE
    SYNTAX      DisplayString (SIZE (0..255))
    MAX-ACCESS  read-only
    STATUS      current
    DESCRIPTION
            "A string to describe the board temperature." 
    ::= { slot16Entry 5 }   


slot16Module OBJECT IDENTIFIER ::= { slot16 2 }

-- slot16ModuleTable --
slot16ModuleTable OBJECT-TYPE
    SYNTAX      SEQUENCE OF Slot16ModuleEntry
    MAX-ACCESS  not-accessible
    STATUS      current
    DESCRIPTION
            "A list of all slot16Module's utilization."
    ::= { slot16Module 1 }  

slot16ModuleEntry OBJECT-TYPE
    SYNTAX      Slot16ModuleEntry
    MAX-ACCESS  not-accessible
    STATUS      current
    DESCRIPTION
            "An entry contains a slot16Module's utilization."
    INDEX   { slot16ModuleIndex }
    ::= { slot16ModuleTable 1 }

Slot16ModuleEntry ::=
    SEQUENCE {     
		slot16ModuleIndex                       Integer32,
		slot16ModuleId                           DisplayString,  
		slot16ModuleIfNumber                     Integer32		
    } 

slot16ModuleIndex OBJECT-TYPE
    SYNTAX      Integer32 (1..2147483647)
    MAX-ACCESS  not-accessible
    STATUS      current
    DESCRIPTION
            "A unique value, greater than zero, for each chassis`s slot16."
    ::= { slot16ModuleEntry 1 }

slot16ModuleId OBJECT-TYPE
    SYNTAX      DisplayString (SIZE (0..32))
    MAX-ACCESS  read-only
    STATUS      current
    DESCRIPTION
            "the value of module`s id"
    ::= { slot16ModuleEntry 2 }
  
slot16ModuleIfNumber OBJECT-TYPE
    SYNTAX      Integer32(0..2147483647)
    MAX-ACCESS  read-only
    STATUS      current
    DESCRIPTION
            "The number of network interfaces (regardless of their
            current state) present on this system." 
    ::= { slot16ModuleEntry 3 } 
    
slot16ModuleIfTable OBJECT-TYPE
    SYNTAX      SEQUENCE OF Slot16ModuleIfEntry
    MAX-ACCESS  not-accessible
    STATUS      current
    DESCRIPTION
            "A list of interface entries.  The number of entries is
            given by the value of ifNumber."
    ::= { slot16Module 2 } 
    
slot16ModuleIfEntry OBJECT-TYPE
    SYNTAX      Slot16ModuleIfEntry
    MAX-ACCESS  not-accessible
    STATUS      current
    DESCRIPTION
            "An entry containing management information applicable to a
            particular interface."
    INDEX   { slot16ModuleifIndex }
    ::= { slot16ModuleIfTable 1 }
    
Slot16ModuleIfEntry ::=
    SEQUENCE {
        slot16ModuleifIndex                 InterfaceIndex,  
        slot16ModuleIfId                    DisplayString,  
        slot16ModuleifDescr                 DisplayString,           
        slot16ModuleifType                  IANAifType,   		
        slot16ModuleifMtu                   Integer32,                
        slot16ModuleifSpeed                 Counter64,               
        slot16ModuleifPhysAddress           PhysAddress,              
        slot16ModuleifAdminStatus           INTEGER,                  
        slot16ModuleifOperStatus            INTEGER,                  
        slot16ModuleifLastChange            TimeTicks,                
        slot16ModuleifInOctets              Counter64,                
        slot16ModuleifInUcastPkts           Counter64,                
        slot16ModuleifInNUcastPkts          Counter64,  
        slot16ModuleifInDiscards            Counter64,
        slot16ModuleifInErrors              Counter64,
        slot16ModuleifInFcsErrorPkts        Counter64,
        slot16ModuleifInUnknownProtos       Counter64,	-- deprecated
        slot16ModuleifOutOctets             Counter64,
        slot16ModuleifOutUcastPkts          Counter64,
        slot16ModuleifOutNUcastPkts         Counter64,  -- deprecated
        slot16ModuleifOutDiscards           Counter64,
        slot16ModuleifOutErrors             Counter64,
        slot16ModuleifOutFcsErrorPkts       Counter64,
        slot16ModuleifOutQLen               Gauge32,    -- deprecated  
        slot16ModuleifOutOctetsRate         Counter64,
        slot16ModuleifInOctetsRate          Counter64,
        slot16ModuleifOutPktsRate           Counter64,
        slot16ModuleifInPktsRate            Counter64,
        slot16ModuleifRxPower               DisplayString,
        slot16ModuleifTxPower               DisplayString,
        slot16ModuleifSpecific              OBJECT IDENTIFIER,
        slot16ModuleifTxMirrorList          DisplayString,
        slot16ModuleifRxMirrorList          DisplayString,
        slot16ModuleifRxPowerMin               DisplayString,
        slot16ModuleifRxPowerMax               DisplayString,
        slot16ModuleifTxPowerMin               DisplayString,
        slot16ModuleifTxPowerMax               DisplayString,
        slot16ModuleifRxHisPeak            Counter64,
        slot16ModuleifTxHisPeak            Counter64,
        slot16ModuleifMode                 DisplayString   		
    }         

slot16ModuleifIndex OBJECT-TYPE
    SYNTAX      InterfaceIndex
    MAX-ACCESS  read-only
    STATUS      current
    DESCRIPTION
            "A unique value, greater than zero, for each interface.  It
            is recommended that values are assigned contiguously
            starting from 1.  The value for each interface sub-layer
            must remain constant at least from one re-initialization of
            the entity's network management system to the next re-
            initialization."
    ::= { slot16ModuleIfEntry 1 }
    
slot16ModuleIfId OBJECT-TYPE
    SYNTAX      DisplayString (SIZE (0..32))
    MAX-ACCESS  read-only
    STATUS      current
    DESCRIPTION
            "the value of module`s id"
    ::= { slot16ModuleIfEntry 2 }
    
slot16ModuleifDescr OBJECT-TYPE
    SYNTAX      DisplayString (SIZE (0..255))
    MAX-ACCESS  read-only
    STATUS      current
    DESCRIPTION
            "A textual string containing information about the
            interface.  This string should include the name of the
            manufacturer, the product name and the version of the
            interface hardware/software."
    ::= { slot16ModuleIfEntry 3 }
    
slot16ModuleifType OBJECT-TYPE
    SYNTAX      IANAifType
    MAX-ACCESS  read-only
    STATUS      current
    DESCRIPTION
            "The type of interface.  Additional values for ifType are
            assigned by the Internet Assigned Numbers Authority (IANA),
            through updating the syntax of the IANAifType textual
            convention."
    ::= { slot16ModuleIfEntry 4 }

slot16ModuleifMtu OBJECT-TYPE
    SYNTAX      Integer32(1..2147483647)
    MAX-ACCESS  read-only
    STATUS      current
    DESCRIPTION
            "The size of the largest packet which can be sent/received
            on the interface, specified in octets.  For interfaces that
            are used for transmitting network datagrams, this is the
            size of the largest network datagram that can be sent on the
            interface."
    ::= { slot16ModuleIfEntry 5 }

slot16ModuleifSpeed OBJECT-TYPE
    SYNTAX      Counter64
    MAX-ACCESS  read-only
    STATUS      current
    DESCRIPTION
            "An estimate of the interface's current bandwidth in bits
            per second.  For interfaces which do not vary in bandwidth
            or for those where no accurate estimation can be made, this
            object should contain the nominal bandwidth. For a sub-layer
            which has no concept of bandwidth, this object should be zero."
    ::= { slot16ModuleIfEntry 6 }

slot16ModuleifPhysAddress OBJECT-TYPE
    SYNTAX      PhysAddress
    MAX-ACCESS  read-only
    STATUS      current
    DESCRIPTION
            "The interface's address at its protocol sub-layer.  For
            example, for an 802.x interface, this object normally
            contains a MAC address.  The interface's media-specific MIB
            must define the bit and byte ordering and the format of the
            value of this object.  For interfaces which do not have such
            an address (e.g., a serial line), this object should contain
            an octet string of zero length."
    ::= { slot16ModuleIfEntry 7 }
    
slot16ModuleifAdminStatus OBJECT-TYPE
    SYNTAX  INTEGER {
                up(1),       -- ready to pass packets
                down(2),
                testing(3)   -- in some test mode
            }
    MAX-ACCESS  read-write
    STATUS      current
    DESCRIPTION
            "The desired state of the interface.  The testing(3) state
            indicates that no operational packets can be passed.  When a
            managed system initializes, all interfaces start with
            ifAdminStatus in the down(2) state.  As a result of either
            explicit management action or per configuration information
            retained by the managed system, ifAdminStatus is then
            changed to either the up(1) or testing(3) states (or remains
            in the down(2) state)."
    ::= { slot16ModuleIfEntry 8 }

slot16ModuleifOperStatus OBJECT-TYPE
    SYNTAX  INTEGER {
                up(1),        -- ready to pass packets
                down(2),
                testing(3),   -- in some test mode
                unknown(4),   -- status can not be determined
                              -- for some reason.
                dormant(5),
                notPresent(6),    -- some component is missing
                lowerLayerDown(7) -- down due to state of
                                  -- lower-layer interface(s)
            }
    MAX-ACCESS  read-only
    STATUS      current
    DESCRIPTION
            "The current operational state of the interface.  The
            testing(3) state indicates that no operational packets can
            be passed.  If ifAdminStatus is down(2) then ifOperStatus
            should be down(2).  If ifAdminStatus is changed to up(1)
            then ifOperStatus should change to up(1) if the interface is
            ready to transmit and receive network traffic; it should
            change to dormant(5) if the interface is waiting for
            external actions (such as a serial line waiting for an
            incoming connection); it should remain in the down(2) state
            if and only if there is a fault that prevents it from going
            to the up(1) state; it should remain in the notPresent(6)
            state if the interface has missing (typically, hardware)
            components."
    ::= { slot16ModuleIfEntry 9 }

slot16ModuleifLastChange OBJECT-TYPE
    SYNTAX      TimeTicks
    MAX-ACCESS  read-only
    STATUS      current
    DESCRIPTION
            "The value of sysUpTime at the time the interface entered
            its current operational state.  If the current state was
            entered prior to the last re-initialization of the local
            network management subsystem, then this object contains a
            zero value."
    ::= { slot16ModuleIfEntry 10 }

slot16ModuleifInOctets OBJECT-TYPE
    SYNTAX      Counter64
    MAX-ACCESS  read-only
    STATUS      current
    DESCRIPTION
            "The total number of octets received on the interface,
            including framing characters.

            Discontinuities in the value of this counter can occur at
            re-initialization of the management system, and at other
            times as indicated by the value of
            ifCounterDiscontinuityTime."
    ::= { slot16ModuleIfEntry 11 }

slot16ModuleifInUcastPkts OBJECT-TYPE
    SYNTAX      Counter64
    MAX-ACCESS  read-only
    STATUS      current
    DESCRIPTION
            "The number of packets, delivered by this sub-layer to a
            higher (sub-)layer, which were not addressed to a multicast
            or broadcast address at this sub-layer.

            Discontinuities in the value of this counter can occur at
            re-initialization of the management system, and at other
            times as indicated by the value of
            ifCounterDiscontinuityTime."
    ::= { slot16ModuleIfEntry 12 }

slot16ModuleifInNUcastPkts OBJECT-TYPE
    SYNTAX  Counter64
    MAX-ACCESS  read-only
    STATUS      current
    DESCRIPTION
            "The number of packets, delivered by this sub-layer to a
            higher (sub-)layer, which were addressed to a multicast or
            broadcast address at this sub-layer.

            Discontinuities in the value of this counter can occur at
            re-initialization of the management system, and at other
            times as indicated by the value of
            ifCounterDiscontinuityTime.

            This object is deprecated in favour of ifInMulticastPkts and
            ifInBroadcastPkts."
    ::= { slot16ModuleIfEntry 13 }

slot16ModuleifInDiscards OBJECT-TYPE
    SYNTAX      Counter64
    MAX-ACCESS  read-only
    STATUS      current
    DESCRIPTION
            "The number of inbound packets which were chosen to be
            discarded even though no errors had been detected to prevent

            their being deliverable to a higher-layer protocol.  One
            possible reason for discarding such a packet could be to
            free up buffer space.

            Discontinuities in the value of this counter can occur at
            re-initialization of the management system, and at other
            times as indicated by the value of
            ifCounterDiscontinuityTime."
    ::= { slot16ModuleIfEntry 14 }

slot16ModuleifInErrors OBJECT-TYPE
    SYNTAX      Counter64
    MAX-ACCESS  read-only
    STATUS      current
    DESCRIPTION
            "For packet-oriented interfaces, the number of inbound
            packets that contained errors preventing them from being
            deliverable to a higher-layer protocol.  For character-
            oriented or fixed-length interfaces, the number of inbound
            transmission units that contained errors preventing them
            from being deliverable to a higher-layer protocol.

            Discontinuities in the value of this counter can occur at
            re-initialization of the management system, and at other
            times as indicated by the value of
            ifCounterDiscontinuityTime."
    ::= { slot16ModuleIfEntry 15 }

slot16ModuleifInFcsErrorPkts OBJECT-TYPE
    SYNTAX      Counter64
    MAX-ACCESS  read-only
    STATUS      current
    DESCRIPTION
            "FCS error pakets."
    ::= { slot16ModuleIfEntry 16 }

slot16ModuleifInUnknownProtos OBJECT-TYPE
    SYNTAX      Counter64
    MAX-ACCESS  read-only
    STATUS      current
    DESCRIPTION
            "For packet-oriented interfaces, the number of packets
            received via the interface which were discarded because of
            an unknown or unsupported protocol.  For character-oriented
            or fixed-length interfaces that support protocol
            multiplexing the number of transmission units received via
            the interface which were discarded because of an unknown or
            unsupported protocol.  For any interface that does not
            support protocol multiplexing, this counter will always be
            0.

            Discontinuities in the value of this counter can occur at
            re-initialization of the management system, and at other
            times as indicated by the value of
            ifCounterDiscontinuityTime."
    ::= { slot16ModuleIfEntry 17 }

slot16ModuleifOutOctets OBJECT-TYPE
    SYNTAX      Counter64
    MAX-ACCESS  read-only
    STATUS      current
    DESCRIPTION
            "The total number of octets transmitted out of the
            interface, including framing characters.

            Discontinuities in the value of this counter can occur at
            re-initialization of the management system, and at other
            times as indicated by the value of
            ifCounterDiscontinuityTime."
    ::= { slot16ModuleIfEntry 18 }

slot16ModuleifOutUcastPkts OBJECT-TYPE
    SYNTAX      Counter64
    MAX-ACCESS  read-only
    STATUS      current
    DESCRIPTION
            "The total number of packets that higher-level protocols
            requested be transmitted, and which were not addressed to a
            multicast or broadcast address at this sub-layer, including
            those that were discarded or not sent.

            Discontinuities in the value of this counter can occur at
            re-initialization of the management system, and at other
            times as indicated by the value of
            ifCounterDiscontinuityTime."
    ::= { slot16ModuleIfEntry 19 }

slot16ModuleifOutNUcastPkts OBJECT-TYPE
    SYNTAX      Counter64
    MAX-ACCESS  read-only
    STATUS      deprecated
    DESCRIPTION
            "The total number of packets that higher-level protocols
            requested be transmitted, and which were addressed to a
            multicast or broadcast address at this sub-layer, including
            those that were discarded or not sent.

            Discontinuities in the value of this counter can occur at
            re-initialization of the management system, and at other
            times as indicated by the value of
            ifCounterDiscontinuityTime.

            This object is deprecated in favour of ifOutMulticastPkts
            and ifOutBroadcastPkts."
    ::= { slot16ModuleIfEntry 20 }

slot16ModuleifOutDiscards OBJECT-TYPE
    SYNTAX      Counter64
    MAX-ACCESS  read-only
    STATUS      current
    DESCRIPTION
            "The number of outbound packets which were chosen to be
            discarded even though no errors had been detected to prevent
            their being transmitted.  One possible reason for discarding
            such a packet could be to free up buffer space.

            Discontinuities in the value of this counter can occur at
            re-initialization of the management system, and at other
            times as indicated by the value of
            ifCounterDiscontinuityTime."
    ::= { slot16ModuleIfEntry 21 }

slot16ModuleifOutErrors OBJECT-TYPE
    SYNTAX      Counter64
    MAX-ACCESS  read-only
    STATUS      current
    DESCRIPTION
            "For packet-oriented interfaces, the number of outbound
            packets that could not be transmitted because of errors.
            For character-oriented or fixed-length interfaces, the
            number of outbound transmission units that could not be
            transmitted because of errors.

            Discontinuities in the value of this counter can occur at
            re-initialization of the management system, and at other
            times as indicated by the value of
            ifCounterDiscontinuityTime."
    ::= { slot16ModuleIfEntry 22 }

slot16ModuleifOutFcsErrorPkts OBJECT-TYPE
    SYNTAX      Counter64
    MAX-ACCESS  read-only
    STATUS      current
    DESCRIPTION
            "FCS error pakets."
    ::= { slot16ModuleIfEntry 23 }

slot16ModuleifOutQLen OBJECT-TYPE
    SYNTAX      Gauge32
    MAX-ACCESS  read-only
    STATUS      deprecated
    DESCRIPTION
            "The length of the output packet queue (in packets)."
    ::= { slot16ModuleIfEntry 24 }

slot16ModuleifOutOctetsRate OBJECT-TYPE
    SYNTAX      Counter64
    MAX-ACCESS  read-only
    STATUS      current
    DESCRIPTION
            "The speed of octets trans on the interface(kbps)"
    ::= { slot16ModuleIfEntry 25 }

slot16ModuleifInOctetsRate OBJECT-TYPE
    SYNTAX      Counter64
    MAX-ACCESS  read-only
    STATUS      current
    DESCRIPTION
            "The speed of octets received on the interface(kbps)"
    ::= { slot16ModuleIfEntry 26 }

slot16ModuleifOutPktsRate OBJECT-TYPE
    SYNTAX      Counter64
    MAX-ACCESS  read-only
    STATUS      current
    DESCRIPTION
            "The speed of packets trans on the interface(pps)"
    ::= { slot16ModuleIfEntry 27 }

slot16ModuleifInPktsRate OBJECT-TYPE
    SYNTAX      Counter64
    MAX-ACCESS  read-only
    STATUS      current
    DESCRIPTION
            "The speed of octets received on the interface(kbps)"
    ::= { slot16ModuleIfEntry 28 }

slot16ModuleifRxPower OBJECT-TYPE
    SYNTAX      DisplayString (SIZE (0..255))
    MAX-ACCESS  read-only
    STATUS      current
    DESCRIPTION
            "the value of interface's received power, in dbm format."
    ::= { slot16ModuleIfEntry 29 }

slot16ModuleifTxPower OBJECT-TYPE
    SYNTAX      DisplayString (SIZE (0..255))
    MAX-ACCESS  read-only
    STATUS      current
    DESCRIPTION
            "the value of interface's send power, in dbm format."
    ::= { slot16ModuleIfEntry 30 }

slot16ModuleifSpecific OBJECT-TYPE
    SYNTAX      OBJECT IDENTIFIER
    MAX-ACCESS  read-only
    STATUS      deprecated
    DESCRIPTION
            "A reference to MIB definitions specific to the particular
            media being used to realize the interface.  It is

            recommended that this value point to an instance of a MIB
            object in the media-specific MIB, i.e., that this object
            have the semantics associated with the InstancePointer
            textual convention defined in RFC 2579.  In fact, it is
            recommended that the media-specific MIB specify what value
            ifSpecific should/can take for values of ifType.  If no MIB
            definitions specific to the particular media are available,
            the value should be set to the OBJECT IDENTIFIER { 0 0 }."
    ::= { slot16ModuleIfEntry 31 }  
  
slot16ModuleifTxMirrorList OBJECT-TYPE
    SYNTAX      DisplayString (SIZE (0..255))
    MAX-ACCESS  read-only
    STATUS      deprecated
    DESCRIPTION
            "the interface tx mirror list."
    ::= { slot16ModuleIfEntry 32 }  
 
slot16ModuleifRxMirrorList OBJECT-TYPE
    SYNTAX      DisplayString (SIZE (0..255))
    MAX-ACCESS  read-only
    STATUS      deprecated
    DESCRIPTION
            "the interface rx mirror list."
    ::= { slot16ModuleIfEntry 33 }  

slot16ModuleifRxPowerMin OBJECT-TYPE
    SYNTAX      DisplayString (SIZE (0..255))
    MAX-ACCESS  read-only
    STATUS      deprecated
    DESCRIPTION
            "the interface min rx power."
    ::= { slot16ModuleIfEntry 34 }  

slot16ModuleifRxPowerMax OBJECT-TYPE
    SYNTAX      DisplayString (SIZE (0..255))
    MAX-ACCESS  read-only
    STATUS      deprecated
    DESCRIPTION
            "the interface max rx power."
    ::= { slot16ModuleIfEntry 35 }  

slot16ModuleifTxPowerMin OBJECT-TYPE
    SYNTAX      DisplayString (SIZE (0..255))
    MAX-ACCESS  read-only
    STATUS      deprecated
    DESCRIPTION
            "the interface min tx power."
    ::= { slot16ModuleIfEntry 36 }  

slot16ModuleifTxPowerMax OBJECT-TYPE
    SYNTAX      DisplayString (SIZE (0..255))
    MAX-ACCESS  read-only
    STATUS      deprecated
    DESCRIPTION
            "the interface max tx power."
    ::= { slot16ModuleIfEntry 37 }  

slot16ModuleifRxHisPeak OBJECT-TYPE
    SYNTAX      Counter64
    MAX-ACCESS  read-only
    STATUS      current
    DESCRIPTION
            "The max speed of rx rate on the interface(kbps)"
    ::= { slot16ModuleIfEntry 38 }

 slot16ModuleifTxHisPeak OBJECT-TYPE
   SYNTAX      Counter64
    MAX-ACCESS  read-only
    STATUS      current
    DESCRIPTION
            "The max speed of tx rate on the interface(kbps)"
    ::= { slot16ModuleIfEntry 39 }

slot16ModuleifMode OBJECT-TYPE
    SYNTAX      DisplayString (SIZE (0..255))
    MAX-ACCESS  read-only
    STATUS      deprecated
    DESCRIPTION
            "the interface if mode."
    ::= { slot16ModuleIfEntry 40 }  

-- The boardPortManagement group --   
-- boardPortManagement --
boardInfoTable OBJECT-TYPE
     SYNTAX      SEQUENCE OF BoardInfoEntry
     MAX-ACCESS  not-accessible
     STATUS      current
     DESCRIPTION
             "A list of all boards's information."
     ::= { boardPortManagement 1 }   
    
boardInfoEntry OBJECT-TYPE
     SYNTAX      BoardInfoEntry
     MAX-ACCESS  not-accessible
     STATUS      current
     DESCRIPTION
             "An entry contains a board's information."
     INDEX   { statusChanged }
     ::= { boardInfoTable 1 } 

BoardInfoEntry ::= 
    SEQUENCE {    
                 statusChanged       DisplayString
     }   
    
statusChanged OBJECT-TYPE
     SYNTAX  DisplayString (SIZE (0..255))
     MAX-ACCESS  read-only
     STATUS      current
     DESCRIPTION
             "Board running status."
     ::= { boardInfoEntry 1 } 

-- traps --

linkProtectStatusChanged NOTIFICATION-TYPE
    STATUS  current
    DESCRIPTION
            "A link protect status changed trap signifies that the SNMP entity,
            acting in an agent role, has detected that the status
            is about to be changed."
    ::= { traps 1 }

cpuStatusChanged NOTIFICATION-TYPE
    STATUS  current
    DESCRIPTION
            "A cpu status change trap signifies that the SNMP entity,
            acting in an agent role, has detected that the cpu 
            status is about to be changed."
    ::= { traps 2 } 

memoryStatusChanged NOTIFICATION-TYPE
    STATUS  current
    DESCRIPTION
            "A memory status change trap signifies that the SNMP entity,
            acting in an agent role, has detected that the memory
            status is about to be changed."
    ::= { traps 3 } 

airFanStatusChanged NOTIFICATION-TYPE
    STATUS  current
    DESCRIPTION
            "A air fan status change trap signifies that the SNMP entity,
            acting in an agent role, has detected that the air fan
            status is about to be changed."
    ::= { traps 4 } 

powerStatusChanged NOTIFICATION-TYPE
    STATUS  current
    DESCRIPTION
            "A power status change trap signifies that the SNMP entity,
            acting in an agent role, has detected that the power 
            status is about to be changed."
    ::= { traps 5 } 


boardTemperatureStatusChanged NOTIFICATION-TYPE
    STATUS  current
    DESCRIPTION
            "A board status changed trap signifies that the SNMP entity,
            acting in an agent role, has detected that the board temperature
            status is about to be changed."
    ::= { traps 6 }

fcsStatusChanged NOTIFICATION-TYPE
    STATUS  current
    DESCRIPTION
            "A interface fcs status changed trap signifies that the SNMP entity,
            acting in an agent role, has detected that the interface's fcs
            status is about to be changed."
    ::= { traps 7 }

dropStatusChanged NOTIFICATION-TYPE
    STATUS  current
    DESCRIPTION
            "A interface drop status changed trap signifies that the SNMP entity,
            acting in an agent role, has detected that the interface's drop
            status is about to be changed."
    ::= { traps 8 }

mtuStatusChanged NOTIFICATION-TYPE
    STATUS  current
    DESCRIPTION
            "A interface mtu status changed trap signifies that the SNMP entity,
            acting in an agent role, has detected that the interface's mtu
            status is about to be changed."
    ::= { traps 9 }

peakcounterStatusChanged NOTIFICATION-TYPE
    STATUS  current
    DESCRIPTION
            "A interface peak counter status changed trap signifies that the SNMP entity,
            acting in an agent role, has detected that the interface's peak counter
            status is about to be changed."
    ::= { traps 10 }

txbytesStatusChanged NOTIFICATION-TYPE
    STATUS  current
    DESCRIPTION
            "A interface tx bytes status changed trap signifies that the SNMP entity,
            acting in an agent role, has detected that the interface's tx bytes
            status is about to be changed."
    ::= { traps 11 }

rxbytesStatusChanged NOTIFICATION-TYPE
    STATUS  current
    DESCRIPTION
            "A interface rx bytes status changed trap signifies that the SNMP entity,
            acting in an agent role, has detected that the interface's rx bytes
            status is about to be changed."
    ::= { traps 12 }

interfaceStatusChanged NOTIFICATION-TYPE
    STATUS  current
    DESCRIPTION
            "A outgroup interface status changed trap signifies that the SNMP entity,
            acting in an agent role, has detected that the outgroup interface's 
            status is about to be changed."
    ::= { traps 13 }

END
